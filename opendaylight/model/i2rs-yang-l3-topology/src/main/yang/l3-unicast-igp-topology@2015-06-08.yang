module l3-unicast-igp-topology {
  yang-version 1;
  namespace "urn:ietf:params:xml:ns:yang:l3-unicast-igp-topology";
  prefix "l3t";
  import ietf-network {
    prefix "nw";
  }
  import ietf-network-topology {
    prefix "nt";
  }
  import ietf-inet-types {
    prefix "inet";
  }
  
  organization "TBD";
  contact "TBD";
  
  description
    "This module defines a model for the layer 3 IGP topology.";
  
  revision "2015-06-08" {
    description "Initial revision";
    reference "TBD";
  }
  
  typedef igp-event-type {
    type enumeration {
      enum "add" {
        value 0;
        description 
          "An IGP node or link or prefix or termination-point has
          been added";
      }
      enum "remove" {
        value 1;
        description 
          "An IGP node or link or prefix or termination-point has
          been removed";
      }
      enum "update" {
        value 2;
        description 
          "An IGP node or link or prefix or termination-point has
          been updated";
      }
    }
    description "IGP Event type for notifications";
  } // igp-event-type

  identity flag-identity {
    description "Base type for flags";
  }
  identity undefined-flag {
    base "flag-identity";
    description "Undefined flag";
  }
  
  typedef flag-type {
    type identityref {
      base "flag-identity";
    }
    description "Type for flags";
  }

  grouping network-ref {
    description
      "Grouping for an absolute reference to a network topology 
      instance.";
    leaf network-ref {
      type leafref {
        path "/nw:network/nw:network-id";
      }
      description
        "An absolute reference to a network topology instance.";
    }
  }

  grouping link-ref {
    description
      "Grouping for an absolute reference to a link instance.";
      uses network-ref;
      leaf link-ref {
        type leafref {
          path "/nw:network"
            +"[nw:network-id = current()/../network-ref]"
            +"/nt:link/nt:link-id";
        }
      description
        "An absolute reference to a link instance.";
    }
  }

  grouping node-ref {
    description
      "Grouping for an absolute reference to a node instance.";
    uses network-ref;
    leaf node-ref {
      type leafref {
        path "/nw:network"
          +"[nw:network-id = current()/../network-ref]"
          +"/nw:node/nw:node-id";
      }
      description
        "An absolute reference to a node instance.";
    }
  }

  grouping tp-ref {
    description
      "Grouping for an absolute reference to a termination point.";
    uses node-ref;
    leaf tp-ref {
      type leafref {
        path "/nw:network"
          +"[nw:network-id = current()/../network-ref]"
          +"/nw:node[nw:node-id = current()/../node-ref]"
          +"/nt:termination-point/nt:tp-id";
      }
      description
        "Grouping for an absolute reference to a termination point.";
    }
  }

  grouping igp-prefix-attributes {
    description
      "IGP prefix attributes";
    leaf prefix {
      type inet:ip-prefix;
      description "IP prefix value";
    }
    leaf metric {
      type uint32;
      description "Prefix metric";
    }
    leaf-list flag {
      type flag-type;
      description "Prefix flags";
    }
  }
  
  grouping l3-unicast-igp-topology-type {
    description "Identify the topology type to be L3 unicast.";
    container l3-unicast-igp-topology {
      presence "indicates L3 Unicast IGP Topology";
      description 
        "The presence of the container node indicates L3 Unicast
        IGP Topology";
    }
  }
  
  grouping igp-topology-attributes {
    description "Topology scope attributes";
    container igp-topology-attributes {
      description "Containing topology attributes";
      leaf name {
        type string;
        description "Name of the topology";
      }
      leaf-list flag {
        type flag-type;
        description "Topology flags";
      }
    }
  }
  
  grouping igp-node-attributes {
    description "IGP node scope attributes";
    container igp-node-attributes {
      description "Containing node attributes";
      leaf name {
        type inet:domain-name;
        description "Node name";
      }
      leaf-list flag {
        type flag-type;
        description "Node operational flags";
      }
      leaf-list router-id {
        type inet:ip-address;
        description "Router-id for the node";
      }
      list prefix {
        key "prefix";
        description 
          "A list of prefixes along with their attributes";
        uses igp-prefix-attributes;
      }
    }
  }

  grouping igp-link-attributes {
    description "IGP link scope attributes";
    container igp-link-attributes {
      description "Containing link attributes";
      leaf name {
        type string;
        description "Link Name";
      }
      leaf-list flag {
        type flag-type;
        description "Link flags";
      }
      leaf metric {
        type uint32 {
          range "0..16777215"  {
            description "
                        ";
            // OSPF/ISIS supports max 3 byte metric.
            // Ideally we would like this restriction to be
            // defined in the derived models, however,
            // we are not allowed to augment a "must" statement.
          }
        }
        description "Link Metric";
      }
    }
  } // grouping igp-link-attributes
  
  grouping igp-termination-point-attributes {
    description "IGP termination point scope attributes";
    container igp-termination-point-attributes {
      description "Containing termination point attributes";
      choice termination-point-type {
        description "Indicates the termination point type";
        case ip {
          leaf-list ip-address {
            type inet:ip-address;
            description "IPv4 or IPv6 address";
          }
        }
        case unnumbered {
          leaf unnumbered-id {
            type uint32;
            description "Unnumbered interface identifier";
          }
        }
      }
    }
  } // grouping igp-termination-point-attributes

  augment "/nw:network/nw:network-types" {
    description 
        "Introduce new network type for L3 unicast IGP topology";
    uses l3-unicast-igp-topology-type;
  }
  
  augment "/nw:network" {
    when "nw:network-types/l3-unicast-igp-topology" {
      description 
        "Augmentation parameters apply only for networks with 
        L3 unicast IGP topology";
    }
    description 
        "Configuration parameters for L3 unicast IPG for the network
        as a whole";
    uses igp-topology-attributes;
  }
  
  augment "/nw:network/nw:node" {
    when "../nw:network-types/l3-unicast-igp-topology" {
      description 
        "Augmentation parameters apply only for networks with 
        L3 unicast IGP topology";
    }
    description 
        "Configuration parameters for L3 unicast IPG at the node 
        level";
    uses igp-node-attributes;
  }
  
  augment "/nw:network/nt:link" {
    when "../nw:network-types/l3-unicast-igp-topology" {
      description 
        "Augmentation parameters apply only for networks with
        L3 unicast IGP topology";
    }
    description "Augment topology link configuration";
    uses igp-link-attributes;
  }

  augment "/nw:network/nw:node/"
         +"nt:termination-point" {
    when "../../nw:network-types/l3-unicast-igp-topology" {
      description 
        "Augmentation parameters apply only for networks with 
        L3 unicast IGP topology";
    }
    description "Augment topology termination point configuration";
    uses igp-termination-point-attributes;
  }
  
  notification igp-node-event {
    description "Notification event for IGP node";
    leaf igp-event-type {
      type igp-event-type;
      description "Event type";
    }
    uses node-ref;
    uses l3-unicast-igp-topology-type;
    uses igp-node-attributes;
  }
  
  notification igp-link-event {
    description "Notification event for IGP link";
    leaf igp-event-type {
      type igp-event-type;
      description "Event type";
    }
    uses link-ref;
    uses l3-unicast-igp-topology-type;
    uses igp-link-attributes;
  }

  notification igp-prefix-event {
    description "Notification event for IGP prefix";
    leaf igp-event-type {
      type igp-event-type;
      description "Event type";
    }
    uses node-ref;
    uses l3-unicast-igp-topology-type;
    container prefix {
      description "Containing IPG prefix attributes";
      uses igp-prefix-attributes;
    }
  }
  
  notification termination-point-event {
    description "Notification event for IGP termination point";
    leaf igp-event-type {
      type igp-event-type;
      description "Event type";
    }
    uses tp-ref;
    uses l3-unicast-igp-topology-type;
    uses igp-termination-point-attributes;
  }
}
