module statistics-manager {

    yang-version 1;
    namespace "urn:opendaylight:params:xml:ns:yang:controller:md:sal:statistics-manager";
    prefix "statistics-manager";

    import config { prefix config; revision-date 2013-04-05; }
    import opendaylight-md-sal-binding { prefix mdsal; revision-date 2013-10-28; }

    description
        "This module contains the base YANG definitions for
        statitics-manager implementation.";

    revision "2014-09-25" {
        description
            "Initial revision.";
    }

    identity statistics-manager {
            base config:module-type;
            config:java-name-prefix StatisticsManager;
    }

    augment "/config:modules/config:module/config:configuration" {
        case statistics-manager {
            when "/config:modules/config:module/config:type = 'statistics-manager'";

            container rpc-registry {
                uses config:service-ref {
                    refine type {
                        mandatory true;
                        config:required-identity mdsal:binding-rpc-registry;
                    }
                }
            }

            container notification-service {
                uses config:service-ref {
                    refine type {
                        mandatory true;
                        config:required-identity mdsal:binding-notification-service;
                    }
                }
            }

            container data-broker {
                uses config:service-ref {
                    refine type {
                        mandatory false;
                        config:required-identity mdsal:binding-async-data-broker;
                    }
                }
            }

            container statistics-manager-settings {
                leaf min-request-net-monitor-interval {
                    type int32;
                }
                leaf max-nodes-for-collector {
                    type int32;
                }
            }
        }
    }

}
