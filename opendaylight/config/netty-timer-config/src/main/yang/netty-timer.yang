// vi: set smarttab et sw=4 tabstop=4:
module netty-timer {
    yang-version 1;
    namespace "urn:opendaylight:params:xml:ns:yang:controller:netty:timer";
    prefix "netty-timer";

    import config { prefix config; revision-date 2013-04-05; }
    import netty { prefix netty; revision-date 2013-11-19; }

    organization "Cisco Systems, Inc.";

    contact "Milos Fabian <milfabia@cisco.com>";

    description
        "This module contains the base YANG definitions for
         netty timer implementation.

        Copyright (c)2013 Cisco Systems, Inc. All rights reserved.;

        This program and the accompanying materials are made available
        under the terms of the Eclipse Public License v1.0 which
        accompanies this distribution, and is available at
        http://www.eclipse.org/legal/epl-v10.html";

    revision "2013-11-19" {
        description
            "Initial revision";
    }

    identity netty-hashed-wheel-timer {
        status deprecated;
        base config:module-type;
        config:provided-service netty:netty-timer;
        config:java-name-prefix HashedWheelTimer;
    }

    augment "/config:modules/config:module/config:configuration" {
        case netty-hashed-wheel-timer {
            when "/config:modules/config:module/config:type = 'netty-hashed-wheel-timer'";

            leaf tick-duration {
                status deprecated;
                type uint32;
            }

            leaf ticks-per-wheel {
                status deprecated;
                type uint16;
            }
        }
    }
}
