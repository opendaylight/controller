module config-test {
    yang-version 1;
    namespace "urn:opendaylight:params:xml:ns:yang:controller:test";
    prefix "test";

    import config { prefix config; revision-date 2013-04-05; }

    description
        "Testing API";

    revision "2013-06-13" {
        description
            "Initial revision";
    }

    identity testing {
        description
            "Test api";

        base "config:service-type";
        config:java-class "org.opendaylight.controller.config.yang.test.impl.CheckedAutoCloseable";
    }
}
