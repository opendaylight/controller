module test-types {
    yang-version 1;
    namespace "urn:opendaylight:params:xml:ns:yang:controller:config:test:types";
    prefix "tt";

    import rpc-context { prefix rpcx; revision-date 2013-06-17; }

    description
        "Types generated for testing";

    revision "2013-11-27";

    typedef extend-once {
        type uint16;
    }

    typedef extend-twice {
        type extend-once;
    }

    typedef extend-enum {
        type enumeration {
            enum "one";
            enum "two";
        }
    }

      typedef unionTest {
        type union {
          type string;
          type uint32;
          type extend-twice;
        }
      }



    identity test-identity1 {

    }

    identity test-identity2 {
        base test-identity1;
    }

    grouping common-operational {
       leaf common-stat {
           type uint64;
       }
       // This would not work, since it clashes with identity common-rpc-ctx from test-groups
       // Both grouping add the same unknown node "rpcx:rpc-context-instance common-rpc-ctx-three;"
       // and we cannot match the unknown node to the grouping that added it
       //rpcx:rpc-context-instance common-rpc-ctx-three;
       rpcx:rpc-context-instance common-rpc-ctx-three;
    }

    //identity common-rpc-ctx;
    identity common-rpc-ctx-three;

    rpc common-rpc-three {
        input {
            uses rpcx:rpc-context-ref {
                refine context-instance {
                    rpcx:rpc-context-instance "common-rpc-ctx-three";
                }
            }
        }

        output {
            leaf output {
                type string;
            }
        }
    }
}
