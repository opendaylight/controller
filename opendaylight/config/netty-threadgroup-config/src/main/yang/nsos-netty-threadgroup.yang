// vi: set smarttab et sw=4 tabstop=4:
module nsos-threadpool {
    yang-version 1;
	namespace "urn:opendaylight:params:xml:ns:yang:controller:netty:threadgroup";
    prefix "netty-t";

    import config { prefix config; revision-date 2013-04-05; }
    import threadpool { prefix th; revision-date 2013-04-09; }

    organization "Cisco Systems, Inc.";

    contact "Robert Varga <rovarga@cisco.com>";

    description
        "This module contains the base YANG definitions for NS-OS
         thread-related services.

        Copyright (c)2013 Cisco Systems, Inc. All rights reserved.";

    revision "2013-11-07" {
        description
            "Initial revision";
    }

    identity netty-threadgroup-fixed {
        base config:module-type;
        config:provided-service th:netty-threadgroup;
        config:java-name-prefix NettyThreadgroup;
    }

    augment "/config:modules/config:module/config:configuration" {
        case netty-threadgroup-fixed {
            when "/config:modules/config:module/config:type = 'netty-threadgroup-fixed'";

            leaf thread-count {
                type uint16;

                description "Number of threads to be used by NioEventLoopGroup. This attribute is optional and default value will be 2* Number of CPUs";
            }

            // TODO add optional thread factory dependency

        }
    }

    augment "/config:modules/config:module/config:state" {
        case netty-threadgroup-fixed {
            when "/config:modules/config:module/config:type = 'netty-threadgroup-fixed'";
        }
    }


}
