module config-jmx-it-impl {
    yang-version 1;
    namespace "urn:opendaylight:params:xml:ns:yang:controller:config:jmx:generator:it:impl";
    prefix "it-impl";

    import config-jmx-it { prefix jmxIt; revision-date 2013-06-13;}
    import config { prefix config; revision-date 2013-04-05; }
    import ietf-inet-types { prefix inet; revision-date 2013-07-15;}
    import config-threads { prefix th; revision-date 2013-04-09; }

    description
        "Testing IMPL";

    revision "2013-04-03" {
        description
            "Initial revision";
    }

    identity impl {
        base config:module-type;
        config:provided-service jmxIt:testing;
        config:java-name-prefix TestImpl;
    }

    identity impl-netconf {
        base config:module-type;
        config:provided-service jmxIt:testing;
        config:java-name-prefix NetconfTestImpl;
    }

    augment "/config:modules/config:module/config:configuration" {
        case impl {
            when "/config:modules/config:module/config:type = 'impl'";

           container dto-a1 {
                leaf simple-arg {
                    type uint32;
                }

                leaf port {
                    type inet:port-number;
                }

            }

            leaf as-number {
                mandatory true;
                type inet:as-number;
            }


            leaf simpleInt1 {
                type uint32;
                default 99L;
            }

            container dto_b {
                leaf simple-int1 {
                    type uint32;
                }

                leaf simple-int2 {
                    type uint32;
                }
            }

        }

        case impl-netconf {
            when "/config:modules/config:module/config:type = 'impl-netconf'";

           container dto-a {
                leaf simple-arg {
                    type uint32;
                }

                container dto-a-inner {
                    leaf simple-arg {
                        type uint32;
                    }

                    container dto-a-inner-inner {
                        leaf simple-arg {
                            type uint32;
                        }
                    }
                }
            }

            leaf simpleInt2 {
                type uint32;
            }

            leaf simpleBoolean {
                type boolean;
                default false;
            }

            leaf simple-long {
                type int64  ;
            }

            leaf simple-long-2 {
                type uint32;
            }

            leaf simple-BigInteger {
                type uint64;
            }

            leaf simple-byte {
                type int8;
            }

            leaf simple-short {
                type uint8;
            }

            leaf simple-test {
                type uint16;
                default 99;
            }

            leaf-list simple-list {
                type uint16;
            }

            container dto_c {
                leaf simple-int1 {
                    type uint32;
                }

                leaf simple-int2 {
                    type uint32;
                }

                leaf simple-int3 {
                    type uint16;
                }

                leaf-list simple-list {
                    type uint16;
                }

                list complex-dto-bInner {
                    leaf-list simple-list {
                        type uint16;
                    }
                    leaf simple-int3 {
                        type uint16;
                    }

                    container deep {
                        leaf simple-int3 {
                            type uint16;
                        }
                    }
                }
            }

            list complex-list {
                list simple-list {
                    leaf simple-int3 {
                        type uint16;
                    }
                }
            }

            list peers {
                    config:java-name-prefix Peer;
                    leaf port {
                        type string;
                    }
                    leaf core-size {
                        type uint32;
                    }
                    leaf simple-int3 {
                        type uint16;
                    }
            }

            container thread-factory {
                uses config:service-ref {
                    refine type {
                        mandatory false;
                        config:required-identity th:threadfactory;
                    }
                    refine name {
                        mandatory false;
                    }
                }
            }
        }
    }

    augment "/config:modules/config:module/config:state" {
        case impl {
            when "/config:modules/config:module/config:type = 'impl'";
            // root runtime bean
            leaf created-sessions {
                type uint32;
            }
        }

        case impl-netconf {
            when "/config:modules/config:module/config:type = 'impl-netconf'";
            // root runtime bean
            leaf created-sessions-1 {
                type uint32;
            }

            leaf created-sessions-2 {
                type uint32;
            }

        }
    }

}
