module config-bgp-listener-impl {
    yang-version 1;
    namespace "urn:opendaylight:params:xml:ns:yang:controller:config:bgp:listener:impl";
    prefix "bgpl-impl";

    import ietf-inet-types { prefix inet; }
    import config { prefix config; revision-date 2013-04-05; }

    description
        "This module contains the base YANG definitions for NS-OS
         BGP listener implementation.";

    revision "2013-04-09" {
        description
            "Initial revision";
        reference "NS-OS System Design, version 1.2.";
    }

    identity bgp-listener-impl {
        base config:module-type;
    }

    augment "/config:modules/config:module/config:state" {
        case bgp-listener-impl {
            when "/config:modules/config:module/config:type = 'bgp-listener-impl'";
            container bgp-listener-impl {
                list peers {
                    config:inner-state-bean;
                    leaf port {
                        type inet:port-number;
                        default 179;
                    }
                    leaf core-size {
                        type uint32;
                    }
                }

                leaf as-number {
                    mandatory true;
                    type inet:as-number;
                }
            }
        }
    }
}
