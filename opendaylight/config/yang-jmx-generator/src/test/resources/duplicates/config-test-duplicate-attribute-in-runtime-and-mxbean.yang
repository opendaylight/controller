// vi: set smarttab et sw=4 tabstop=4:
module config-test-duplicate-attribute-in-runtime-and-mxbean {
    yang-version 1;
    namespace "urn:opendaylight:params:xml:ns:yang:controller:jmx:duplicate:runtime";
    prefix "th-java";

    import config { prefix config; revision-date 2013-04-05; }
    import rpc-context { prefix rpcx; revision-date 2013-06-17; }
    import ietf-inet-types { prefix inet; revision-date 2013-07-15;}


    description
        "This module contains the base YANG definitions for NS-OS
         thread services pure Java implementation.";

    revision "2013-04-05" {
        description
            "Updated to work with new anchors.";
    }

    revision "2013-04-03" {
        description
            "Initial revision.";
    }

   identity async-eventbus {
        base config:module-type;
        config:java-name-prefix AsyncEventBus;
    }

    augment "/config:modules/config:module/config:configuration" {
        case async-eventbus {
            when "/config:modules/config:module/config:type = 'async-eventbus'";
            leaf port {
                type string;
            }
            leaf core-size {
                type uint32;
            }
            leaf simple-int3 {
                type uint16;
            }
        }
    }

    augment "/config:modules/config:module/config:state" {
        case async-eventbus {
            when "/config:modules/config:module/config:type = 'async-eventbus'";
            leaf simple-arg {
                type uint32;
            }
            leaf port {
                type inet:port-number;
            }
        }
    }
}
