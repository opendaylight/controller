// vi: set smarttab et sw=4 tabstop=4:
module threadpool {
	yang-version 1;
	namespace "urn:opendaylight:params:xml:ns:yang:controller:threadpool";
	prefix "th";

	import config { prefix config; revision-date 2013-04-05; }

	organization "Cisco Systems, Inc.";

	contact "Robert Varga <rovarga@cisco.com>";

    description
        "This module contains the base YANG definitions for
         thread-related services.

        Copyright (c)2013 Cisco Systems, Inc. All rights reserved.;

        This program and the accompanying materials are made available
		under the terms of the Eclipse Public License v1.0 which
		accompanies this distribution, and is available at
		http://www.eclipse.org/legal/epl-v10.html";

    revision "2013-04-09" {
        description
            "Added eventbus service.";
    }

    revision "2013-04-05" {
        description
            "Updated with YANG extension for Java class specification.";
    }

    revision "2013-04-03" {
        description
            "Initial revision by Anton Tkacik, Tomas Olvecky and
             Robert Varga.";
    }

    identity eventbus {
        description
            "Service representing an event bus. The service acts as message
             router between event producers and event consumers";

        base "config:service-type";
        config:java-class "com.google.common.eventbus.EventBus";
    }

    identity threadfactory {
        description
            "Service representing a ThreadFactory instance. It is directly
             useful in Java world, where various library pieces need to create
             threads and you may want to inject a customized thread
             implementation.";

        base "config:service-type";
        config:java-class "java.util.concurrent.ThreadFactory";
    }

	identity threadpool {
        description
            "A simple pool of threads able to execute work.";

		base "config:service-type";
        config:java-class "org.opendaylight.controller.config.threadpool.ThreadPool";
	}

	identity scheduled-threadpool {
        description
            "An extension of the simple pool of threads able to schedule
             work to be executed at some point in time.";

		base "threadpool";
        config:java-class "org.opendaylight.controller.config.threadpool.ScheduledThreadPool";
	}
}
