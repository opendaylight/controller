/*
 * Copyright (c) 2014 Inocybe Technologies, Inc. and others.  All rights reserved.
 *
 * This program and the accompanying materials are made available under the
 * terms of the Eclipse Public License v1.0 which accompanies this distribution,
 * and is available at http://www.eclipse.org/legal/epl-v10.html
 */

module bundles {
	yang-version 1;

	namespace "urn:opendaylight:controller:bundles";
    prefix bundles-service;

    import bundles-service-groupings{prefix bundles-service-groupings;}
    import bundles-common{prefix bundles-common;}

    contact
      "Gabriel Robitaille-Montpetit <grmontpetit@inocybe.com>";

    revision 2015-01-11 {
        description
            "3rd revision: Bundles Service to add / remove bundles via RESTConf";
    }

    container bundle {
        uses bundles-service-groupings:bundle-fields;
        description "The reprensentation of a bundle.";
        config true;
        leaf bundleServiceStatus{
            type enumeration{
                enum "available"{
                    value 1;
                    description
                        "The bundle service is available to install / uninstall bundle.";
                }
                enum "unavailable"{
                    value 2;
                    description
                        "The bundle service is unavailable to install / uninstall bundle.";
                }
            }
        }
    }

    rpc install-bundle {
        description "Used to install a bundle by providing its name and optional field version.";
        input {
          uses bundles-service-groupings:bundle-fields;
        }
        output {
            uses bundles-service-groupings:operation-result;
        }
      }

    rpc uninstall-bundle {
        description "Used to uninstall a bundle by providing its location and optional field version.";
        input {
            uses bundles-service-groupings:bundle-fields;
        }
        output {
            uses bundles-service-groupings:operation-result;
        }
    }

    rpc list-bundles {
        description "used to list the bundles in the system.";
        output {
            uses bundles-service-groupings:bundle-list;
        }
    }
}
