module augment-network-link-attributes {
    yang-version 1;
    namespace "urn:model:augment:network:link:attributes";
    prefix "tp";

    import abstract-topology {
        prefix "at";
        revision-date 2013-02-08;
    }

    organization "OPEN DAYLIGHT";
    contact "http://www.opendaylight.org/";

    revision "2013-05-03" {
        reference "http://www.opendaylight.org/";
    }

    augment "at:topology/at:network-links/at:network-link/at:attributes" {
        leaf longitude {
            type decimal64 {    
                fraction-digits 2;
            }
        }

        leaf latitude {
            type decimal64 {    
                fraction-digits 2;
            }
        }
    }
}
