module binary-types {

   namespace "urn:binary:types";
   prefix "bin";

   organization "OPEN DAYLIGHT";

   contact "http://www.opendaylight.org/";

   description "Stand alone binary types declaration file for testing
   purposes only.";

   revision 2013-06-13 {
     description
      "Initial revision.";
     reference
      "NO REFERENCE";
   }

   /*** collection of protocol field related types ***/

   typedef simple-binary {
     type binary;
   }

   typedef restricted-binary {
     type binary {
        length 24;
     }
   }

   typedef composite-binary {
     type union {
        type bin:simple-binary;
        type bin:restricted-binary;
     }
   }
 }
