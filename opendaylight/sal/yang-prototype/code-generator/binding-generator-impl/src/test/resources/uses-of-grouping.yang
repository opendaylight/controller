module grouping_uses {

    namespace "urn:uses:of:grouping";
    prefix "sbd";

    organization "OPEN DAYLIGHT";
    contact "http://www.opendaylight.org/";

    revision 2013-07-18 {
    }


  
    grouping grouping-modul-test {
        leaf leaf-grouping-modul-test {
            type string;
        }
        leaf leaf-grouping-modul-test2 {
            type uint8;
        }
    }

    grouping grouping-container-test {
        leaf leaf-grouping-container-test1 {
            type string;
        }
        leaf leaf-grouping-container-test2 {
            type uint8;
        }
    }

    grouping grouping-case-test {
        leaf leaf-grouping-case-test1 {
            type string;
        }     
    }

    grouping grouping-choice-test {
        choice choice-grouing-choice-test {
            case case-choice-grouping-choice-test1 {
                leaf leaf-case-choice-grouping-choice-test1 {
                    type string;
                }
            }
            case case-choice-grouping-choice-test2 {
                leaf leaf-case-choice-grouping-choice-test2 {
                    type uint8;
                }
            }
        }
    }
 
    grouping grouping-list-test {
        leaf leaf-grouping-list-test {
            type string;
        }
        container container-grouping-list-test {
            leaf leaf-container-grouping-list-test {
                type uint8;
            }
        }
        list list-grouping-list-test {
            leaf leaf-list-grouping-list-test {
                type int32;
            }
        }
        leaf-list leaflist-grouping-list-test {
            type string;
        }
    }     

    grouping grouping-grouping-test {
        leaf leaf-grouping-grouping {
            type string;
        }
    }

    grouping grouping-rpc-input-test {
        container container-grouping-rpc-input-test {
            leaf leaf-container-grouping-rpc-input-test {
                type string;
            }
        }
        leaf-list leaflist-grouping-rpc-input-test {
            type uint8;
        }
    }
    
    grouping grouping-rpc-output-test {
        leaf leaf-grouping-rpc-output-test {
            type int8;
        }
    }
     
//grouping in GROUPING
    grouping grouping-atest {
        leaf leaf-grouping-test {
            type int8;
        }
        uses grouping-grouping-test;
    }
    
//grouping in MODUL     
//     uses grouping-modul-test;

//grouping in RPC
        rpc rpc-test {
            input {
                uses grouping-rpc-input-test;
            }
            output {
                uses grouping-rpc-output-test;
            }
        }     

//grouping in CONTAINER
    container container-test {
        leaf container-leaf-test {
            type string;
        }
        uses grouping-container-test;
    }

//grouping in CASE     
    container container-with-choicetest {
        choice choice-test {
            case a {
                leaf leaf-choice-test1 {
                    type string;
                }
            }
            case c {                 
                uses grouping-case-test;                 
            }
        }     
    }  
 
//grouping in LIST     
    list list-test {
        leaf list-leaf-test {
            type string;
        }
        uses grouping-list-test;
    }   
}
