module grouping_uses_rpc {
    
    namespace "urn:grouping:uses:rpc";
    prefix "sbd";

    organization "OPEN DAYLIGHT";
    contact "http://www.opendaylight.org/";

    revision 2013-07-18 {
    }

     

    grouping grouping-rpc-input-test {
        container container-grouping-rpc-input-test {
            leaf leaf-container-grouping-rpc-input-test {
                type string;
            }
        }
        leaf-list leaflist-grouping-rpc-input-test {
            type uint8;
        }
    }
    
    grouping grouping-rpc-output-test {
        leaf leaf-grouping-rpc-output-test {
            type int8;
        }
    }

//grouping in RPC
    rpc rpc-test {
        input {
            uses grouping-rpc-input-test;
        }
        output {
            uses grouping-rpc-output-test;
        }
    }
}
