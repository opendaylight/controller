module grouping_uses_case {

    namespace "urn:grouping:uses:case";
    prefix "sbd";

    organization "OPEN DAYLIGHT";
    contact "http://www.opendaylight.org/";

    revision 2013-07-18 {
    }


    grouping grouping-case-test {
        leaf leaf-grouping-case-test1 {
            type string;
        }
    }

    grouping grouping-choice-test {
        choice choice-grouing-choice-test {
            case case-choice-grouping-choice-test1 {
                leaf leaf-case-choice-grouping-choice-test1 {
                    type string;
                }
            }
            case case-choice-grouping-choice-test2 {
                leaf leaf-case-choice-grouping-choice-test2 {
                    type uint8;
                }
            }
        }
    }

//grouping in CASE
    container container-with-choicetest {
        choice choice-test {
            case a {
                leaf leaf-choice-test1 {
                    type string;
                }
            }
            case c {
                uses grouping-case-test;
            }
        }
    }
}
