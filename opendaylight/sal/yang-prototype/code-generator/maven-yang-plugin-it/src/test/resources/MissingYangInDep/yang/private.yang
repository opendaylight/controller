module private {
    yang-version 1;
    namespace "urn:simple.container.demo";
    prefix "p";

    import unknownDep {
        prefix "data";
        revision-date 2013-02-27;
    }

    organization "opendaylight";
    contact "http://www.opendaylight.org/";

    revision "2013-02-27" {
        reference " WILL BE DEFINED LATER";
    }
    

}
