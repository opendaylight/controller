module custom-types-test {

	yang-version 1;
    namespace "urn:simple.container.demo";
    prefix "iit";
    
    organization "opendaylight";
    contact "WILL-BE-DEFINED-LATER";
        revision 2012-04-16 {
    }
    
    
    typedef access-operations-type {
        type bits {
            bit create {
                description "Any protocol operation that creates a new data node.";
            }
            bit read {
                description "Any protocol operation or notification that returns the value of a data node.";
                position 500;
            }
            bit update {
                description "Any protocol operation that alters an existing data node.";
            }
            bit delete {
                description "Any protocol operation that removes a data node.";
                position 365;
            }
            bit exec {
                description "Execution access to the specified protocol operation.";
            }
        }
        description "NETCONF Access Operation.";
    }
     
    leaf inst-id-leaf1 {
        type instance-identifier {
     	    require-instance false;
        }
    }
     
    leaf inst-id-leaf2 {
        type instance-identifier;
    }

    identity crypto-base {
        description "crypto-base description";
    }
     
    identity crypto-alg {
        base "crypto-base";
        description "crypto-alg description";
    }
    
    leaf mybits {
        type bits {
            bit disable-nagle {
                position 0;
            }
            bit auto-sense-speed {
                position 1;
            }
            bit 10-Mb-only {
                position 2;
            }
        }
        default "auto-sense-speed";
    }
    
   typedef ip-version {
     type enumeration {
       enum unknown {
         description
          "An unknown or unspecified version of the Internet protocol.";
       }
       enum ipv4 {
         value "19";
         description
          "The IPv4 protocol as defined in RFC 791.";
       }
       enum ipv6 {
         value "7";
         description
          "The IPv6 protocol as defined in RFC 2460.";
       }
       enum default {
         description 
          "default ip";
       }
     }
   }
   
  identity service-type {
    description
            "Service identity base type. All service identities must be
             derived from this type. A service type uniquely defines a single
             atomic API contract, such as a Java interface, a set of C
             function declarations, or similar.

             If the service type has a corresponding Java interface, the name
             of that interface should be attached to the derived identity MUST
             include a java-class keyword, whose name argument points to that
             interface.";
  }

  typedef service-type-ref {
    description
            "Internal type of references to service type identity.";

    type identityref {
      base service-type;
    }
  }

}
