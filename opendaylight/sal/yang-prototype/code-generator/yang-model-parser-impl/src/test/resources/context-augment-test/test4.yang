module test4 {

    yang-version 1;
    namespace "urn:simple.demo.test4";
    prefix "t4";

    organization "opendaylight";
    contact "WILL-BE-DEFINED-LATER";
        revision 2013-06-18 {
    }

    container interfaces {
         list ifEntry {
             key "ifIndex";
             leaf ifIndex {
                 type uint32;
                 units minutes;
             }
             leaf ifMtu {
                 type int32;
             }
             min-elements 1;
             max-elements 11;
         }
    }

}
