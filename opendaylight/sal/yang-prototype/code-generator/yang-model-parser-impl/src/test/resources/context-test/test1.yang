module test1 {

    yang-version 1;
    namespace "urn:simple.demo.test1";
    prefix "t1";
    
    import ietf-inet-types {
        prefix "inet";
        revision-date 2010-09-24;
    }
    
    organization "opendaylight";
    contact "WILL-BE-DEFINED-LATER";
        revision 2013-06-18 {
    }
    
    typedef dscp-ext {
        type inet:dscp {
            range "min..max";
        }
    }

    leaf id {
        type inet:port-number {
            range "0..65536";
        }
    }

}
