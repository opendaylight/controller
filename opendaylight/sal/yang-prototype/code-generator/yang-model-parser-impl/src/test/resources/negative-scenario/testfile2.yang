module test2 {
    yang-version 1;
    namespace "urn:simple.types.data.demo";
    prefix "t2";
    
    organization "opendaylight";
    contact "http://www.opendaylight.org/";
    
    description "This is types-data test description";

    revision "2013-02-27" {
        reference " WILL BE DEFINED LATER";
    }
    
    container c1 {
        typedef int-ext {
            type int32 {
                range "10..20";
            }
        }
    }
    
    container top {
        leaf id {
            type int-ext;
        }
    }

}
