module controller-openflow-ipv6 {
	yang-version 1;
	namespace "urn:opendaylight:controller:network:openflow:ipv6";
	prefix "of6";

	import controller-network {
		prefix cn;
	}
	import ietf-inet-types { prefix "inet"; }
	import controller-openflow-ne {prefix "of";}

	revision 2013-06-07 {
	   description "Initial demo";
	}
}
