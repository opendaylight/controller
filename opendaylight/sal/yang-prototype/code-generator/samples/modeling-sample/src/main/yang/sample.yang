module sample {
    yang-version 1;
    namespace "sample";
    prefix "s";

    revision 2013-06-13 {
       description "Initial demo";
    }
    


    // Simple Type definition
    
    typedef foo-name {
        type string;
    }
    
    // Storage / data structure
    
    container topologies {
        list topology {
            leaf foo-name {
                type string;
            }
        }
    }
    
    
    // Notification / Event
    
    notification packet-in {
        leaf node {
            type string;
        }
        leaf port {
            type uint16;
        }
        leaf content {
            type binary;
        }
    }
    
    // RPC
    
    rpc packet-out {
        input {
            leaf node {
                type string;
            }
            leaf port {
                type uint16;
            }
            leaf content {
                type binary;
            }
        }
        output {
            
        }
    }    

}
