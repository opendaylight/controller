module opendaylight-flow-statistics {
    namespace "urn:opendaylight:flow:statistics";
    prefix flowstat;

    import yang-ext {prefix ext;}
    import ietf-inet-types {prefix inet;}
    import ietf-yang-types {prefix yang;}
    import opendaylight-flow-base {prefix flow;}
    import opendaylight-inventory {prefix inv;}

    revision "2013-08-19" {
        description "Initial revision of flow service";
    }

    /*
    augment "/flow:flows/flow:flow" {
        ext:augment-identifier "flow-statistics";

        leaf packet-count {
            type uint64;
        } 

        leaf byte-count {
            type uint64;
        }

        container duration {
            leaf second {
                type uint64;
            }
            leaf nanosecond {
                type uint64;
            }
        }
    }
    */

    augment "/inv:nodes/inv:node/inv:node-connector" {
        ext:augment-identifier "node-connector-statistics";

        container packets {
            leaf received {
                type uint64;
            }
            leaf transmitted {
                type uint64;
            }
        }
        container bytes {
            leaf received {
                type uint64;
            }
            leaf transmitted {
                type uint64;
            }
        }
        leaf receive-drops {
            type uint64;
        }
        leaf transmit-drops {
            type uint64;
        }
        leaf receive-errors {
            type uint64;
        }
        leaf transmit-errors {
            type uint64;
        }
        leaf receive-frame-error {
            type uint64;
        }
        leaf receive-over-run-error {
            type uint64;
        }
        leaf receive-crc-error {
            type uint64;
        }
        leaf collision-count {
            type uint64;
        }

    }

}
