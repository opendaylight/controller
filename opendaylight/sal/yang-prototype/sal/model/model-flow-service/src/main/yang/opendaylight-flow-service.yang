module opendaylight-flow-service {
    namespace "urn:opendaylight:flow:service";
    prefix flow;

    import yang-ext {prefix ext;}
    import opendaylight-inventory {prefix inv;}
    import opendaylight-flow-base {prefix flowbase;}

    revision "2013-08-19" {
        description "Initial revision of flow service";
    }

    /** Base configuration structure **/
    

    grouping flow-update {
        container original-flow {
            uses flowbase:flow;
        }
        container updated-flow {
            uses flowbase:flow;
        }
    }

    rpc add-flow {
        input {
            uses flowbase:flow;
        }
    }

    rpc remove-flow {
        input {
            uses flowbase:flow;
        }
    }

    rpc update-flow {
        input {
            uses flow-update;
        }
    }

    notification flow-added {
        uses flowbase:flow;
    }

    notification flow-updated {
        input {
            uses flow-update;
        }
    }

    notification flow-removed {
        uses flowbase:flow;
    }
}
