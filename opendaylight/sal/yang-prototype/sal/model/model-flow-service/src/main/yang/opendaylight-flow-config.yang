module opendaylight-flow-config {
    namespace "urn:opendaylight:flow:config";
    prefix flow;

    import yang-ext {prefix ext;}
    import opendaylight-inventory {prefix inv;}
    import opendaylight-flow-base {prefix flowbase;}

    revision "2013-08-19" {
        description "Initial revision of flow service";
    }

    /** Base configuration structure 
    container flows {
        list flow {
            uses flowbase:flow;
        }
    }

    **/
}
