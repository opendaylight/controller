module netconf-auth {
    yang-version 1;
    namespace "urn:opendaylight:params:xml:ns:yang:controller:config:netconf:auth";
    prefix "na";

    import config { prefix config; revision-date 2013-04-05; }

    description
        "This module contains the base YANG definitions for
         netconf northbound server API";

    revision "2015-07-15" {
        description
            "Initial revision.";
    }

    identity netconf-auth-provider {
        base "config:service-type";
        config:java-class "org.opendaylight.controller.netconf.auth.AuthProvider";
    }

}
