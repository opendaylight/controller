// vi: set smarttab et sw=4 tabstop=4:
module odl-netconfig-client-cfg {

    yang-version 1;
    namespace "urn:opendaylight:params:xml:ns:yang:controller:config:netconf:client:dispatcher";
    prefix "cfg-net-client";

    import config { prefix config; revision-date 2013-04-05; }
    import odl-netconf-cfg { prefix cfg-net; revision-date 2014-04-08; }
    import netty {prefix netty; }

    description
        "This module contains the base YANG definitions for
        netconf-client-dispatcher implementation.

        Copyright (c)2013 Cisco Systems, Inc. All rights reserved.;

        This program and the accompanying materials are made available
        under the terms of the Eclipse Public License v1.0 which
        accompanies this distribution, and is available at
        http://www.eclipse.org/legal/epl-v10.html";

    revision "2014-04-08" {
        description
            "Initial revision.";
    }

    identity netconf-client-dispatcher {
            base config:module-type;
            config:provided-service cfg-net:netconf-client-dispatcher;
            config:java-name-prefix NetconfClientDispatcher;
    }

    augment "/config:modules/config:module/config:configuration" {
        case netconf-client-dispatcher {
            when "/config:modules/config:module/config:type = 'netconf-client-dispatcher'";

            container boss-thread-group {
                uses config:service-ref {
                    refine type {
                        config:required-identity netty:netty-threadgroup;
                    }
                }
            }

            container worker-thread-group {
                uses config:service-ref {
                    refine type {
                        config:required-identity netty:netty-threadgroup;
                    }
                }
            }

            container timer {
                uses config:service-ref {
                    refine type {
                        config:required-identity netty:netty-timer;
                    }
                }
            }
        }
    }

}
