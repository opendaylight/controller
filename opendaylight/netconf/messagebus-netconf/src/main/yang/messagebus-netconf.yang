module messagebus-netconf {
    yang-version 1;
    namespace "urn:opendaylight:params:xml:ns:yang:controller:messagebus:netconf";
    prefix "msgb-netconf";

    import config { prefix config; revision-date 2013-04-05; }
    import opendaylight-md-sal-binding {prefix sal;}
    import opendaylight-md-sal-dom {prefix dom;}
    import messagebus-event-source-registry {prefix esr;}

    description
        "Message bus netconf event source";

    revision "2015-07-28" {
        description "Message bus netconf event source initial definition";
    }

    identity messagebus-netconf {
        base config:module-type;
        config:java-name-prefix MessageBusNetconf;
    }

    augment "/config:modules/config:module/config:configuration" {
        case messagebus-netconf {
            when "/config:modules/config:module/config:type = 'messagebus-netconf'";

            container event-source-registry {
                uses config:service-ref {
                    refine type {
                        mandatory true;
                        config:required-identity esr:event-source-registry;
                    }
                }
            }

            container dom-broker {
                uses config:service-ref {
                    refine type {
                        mandatory true;
                        config:required-identity dom:dom-broker-osgi-registry;
                    }
                }
            }

            container binding-broker {
                uses config:service-ref {
                    refine type {
                        mandatory true;
                        config:required-identity sal:binding-broker-osgi-registry;
                    }
                }
            }

            list namespace-to-stream {
                key urn-prefix;

                leaf urn-prefix {
                    type string;
                }

                leaf stream-name {
                    type string;
                }
            }

        }
    }
}
