// vi: set smarttab et sw=4 tabstop=4:
module odl-netconf-cfg {

    yang-version 1;
    namespace "urn:opendaylight:params:xml:ns:yang:controller:config:netconf";
    prefix "cfg-net";

    import config { prefix config; revision-date 2013-04-05; }

    description
        "This module contains the base YANG definitions for
        netconf related services.

        Copyright (c)2013 Cisco Systems, Inc. All rights reserved.;

        This program and the accompanying materials are made available
        under the terms of the Eclipse Public License v1.0 which
        accompanies this distribution, and is available at
        http://www.eclipse.org/legal/epl-v10.html";

    revision "2014-04-08" {
        description
            "Initial revision.";
    }

    identity netconf-client-dispatcher {

        base "config:service-type";
        config:java-class "org.opendaylight.controller.netconf.client.NetconfClientDispatcher";
    }
}
