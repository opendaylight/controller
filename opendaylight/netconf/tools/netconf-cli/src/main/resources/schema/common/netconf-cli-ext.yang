module netconf-cli-ext {

  namespace "urn:ietf:params:xml:ns:netconf:base:1.0:cli";

  prefix cliext;

    revision 2014-05-26 {
      description
        "Initial revision";
    }

  extension argument-handler {
    description
        "Links custom argument reader to an input argument";
    argument "name";
  }

}
