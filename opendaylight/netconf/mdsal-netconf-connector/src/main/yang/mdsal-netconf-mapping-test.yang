module config {
    yang-version 1;
    namespace "urn:opendaylight:mdsal:mapping:test";
    prefix "map";

    revision "2015-02-26";

    container mapping-nodes {

        list mapping-node{
            key "id";
            leaf id {
                type string;
            }

            leaf content {
                type string;
            }
        }
    }

    container top {

        container users {

            list user {

                leaf name {
                    type string;
                }

                leaf type {
                    type string;
                }

                leaf full-name {
                    type string;
                }

                container company-info {

                    leaf dept {
                        type string;
                    }

                    leaf id {
                        type string;
                    }
                }
            }
        }

        container modules {

            list module {

                leaf id {
                    type string;
                }

                leaf type {
                    type string;
                }

                leaf desc {
                    type string;
                }
            }
        }

        choice choice-node {
            case a {
                leaf text {
                    type string;
                }
            }

            case b {
                container text-cont {
                    leaf text {
                        type string;
                    }
                }
            }
        }

    } //top

    augment "/map:top/map:choice-node" {
        case c {
            leaf augmented-case {
                type string;
            }
        }

        case d {
            container choice-wrapper {
                choice inner-choice {
                    case ia {
                        leaf text {
                            type string;
                        }
                    }

                    case ib {
                        leaf text2 {
                            type string;
                        }
                    }
                }
            }
        }
    }

    augment "/map:top/map:modules/" {
        container augmented-container{
            leaf identifier {
                type string;
            }
        }
    }
}
