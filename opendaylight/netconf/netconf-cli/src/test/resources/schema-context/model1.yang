module model1 {
  namespace "ns:model1";
  prefix "mod1";

  revision "2014-05-14" {
  }

  container cont1 {
    container cont11 {
        list lst111 {
            key lf1111;
            leaf lf1111 {
                type int32;
            }
            container cont111 {
                leaf lf1112 {
                    type string;
                }
                leaf-list lflst1111 {
                    type int8;
                }
            }
        }
    }

    container cont12 {
        list lst121 {
            key lf1211;
            leaf lf1211 {
                type string;
            }
            list lst1211 {
                leaf lf12111 {
                    type uint8;
                }
                leaf lf12112 {
                    type string;
                }
            }
        }
        choice chcA {
            case AA {
                leaf lf12AA1 {
                    type string;
                }
            }
            case AB {
                container cont12AB1 {
                    leaf lf12AB1 {
                        type string;
                    }
                }
            }
            leaf lf121 { //should be standalone case
                type string;
            }
        }
        list lst122 {
        }
    }
  }

  container cont2 {
    container cont23 {
    }
  }

  container contA {
  }

  container contB {
  }

}
