module model2 {
  namespace "ns:model2";
  prefix "mod2";

  import model1 {prefix model1; revision-date 2014-05-14;}

  revision "2014-05-14" {
  }

  container contA {
  }

  container contB {
  }

  augment "/model1:cont2" {
    container cont21 {
    }

    container cont22 {
    }
  }

  augment "/model1:cont1" {
    list lst11 {
       leaf lf111 {
        type string;
       }
    }
  }

}
