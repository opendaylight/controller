/*
 * This module has been generated by smidump 0.4.8:
 *
 *      smidump -f yang DOCS-IF-MIB
 *
 * Do not edit. Edit the source file instead!
 */

module DOCS-IF-MIB {

  /*** NAMESPACE / PREFIX DEFINITION ***/

  namespace "urn:ietf:params:xml:ns:yang:smiv2:DOCS-IF-MIB";
  prefix "docs-if";

  /*** LINKAGE (IMPORTS / INCLUDES) ***/

  import IANAifType-MIB   { prefix "ianaiftype-mib"; }
  import IF-MIB           { prefix "if-mib"; }
  import INET-ADDRESS-MIB { prefix "inet-address"; }
  import SNMPv2-TC        { prefix "smiv2"; }
  import ieee-types       { prefix "ieee"; }
  import ietf-inet-types       { prefix "inet"; }
  import ietf-yang-types {
    prefix "yang";
    revision-date "2010-09-24";
  }

  /*** META INFORMATION ***/

  organization
   "IETF IPCDN Working Group";

  contact           
   "        David Raftus
    Postal: ATI Technologies Inc.
            340 Terry Fox Drive, Suite 202
            Ottawa Ontario
            Canada
    Phone:  +1 613 592 1052 ext.222
    E-mail: david.raftus@ati.com
    
            Eduardo Cardona
    Postal: Cable Television Laboratories, Inc.
            858 Coal Creek Circle
            Louisville, CO 80027-9750
            U.S.A.
    Phone:  Tel:    +1 303 661 9100
            Fax:    +1 303 661 9199
    E-mail: e.cardona@cablelabs.com;mibs@cablelabs.com
    
    IETF IPCDN Working Group
    General Discussion: ipcdn@ietf.org
    Subscribe: http://www.ietf.org/mailman/listinfo/ipcdn
    Archive: ftp://ftp.ietf.org/ietf-mail-archive/ipcdn
    Co-chairs: Richard Woundy, Richard_Woundy@cable.comcast.com
               Jean-Francois Mule, jf.mule@cablelabs.com";

  description       
   "This is the MIB Module for DOCSIS 2.0-compliant Radio
    Frequency (RF) interfaces in Cable Modems and
    Cable Modem Termination Systems.
    
    Copyright (C) The Internet Society (2006).  This
    version of this MIB module is part of RFC 4546; see
    the RFC itself for full legal notices.";

  revision "2006-05-24" {
    description     
     "Revision of the IETF RF MIB module for DOCSIS 2.0.
      This version published as RFC 4546.
      This MIB module revision includes the following
      among others:
      Usage of ifType (205) for upstream logical channels.
      Addition of downstream and upstream utilization
      counters.
      Additional statistics per upstream interface.
      Upstream channel offline configuration mechanism.
      Added MIB support for new DOCSIS 2.0 modulation
      attributes.
      Euro-DOCSIS downstream interleave values.
      Adjustments to RFC 2670 definitions based on
      the MIB review guidelines from the IETF
      
      
      Operations and Management Area (OPS).";
  }
  revision "1999-08-19" {
    description     
     "Initial version, published as RFC 2670.
      Modified by Mike St. Johns to fix problems identified by
      the first pass of the MIB doctor.  Of special note,
      docsIfRangingResp and docsIfCmtsInsertionInterval were
      obsoleted and replaced by other objects with the same
      functionality, but with more appropriate syntax.";
  }

  /*** TYPE DEFINITIONS ***/

  typedef TenthdBmV {
    type int32;
    description     
     "This data type represents power levels that are normally
      expressed in dBmV.  Units are in tenths of a dBmV;
      for example, 5.1 dBmV will be represented as 51.";
  }

  typedef TenthdB {
    type int32;
    description     
     "This data type represents power levels that are normally
      expressed in dB.  Units are in tenths of a dB;
      for example, 5.1 dB will be represented as 51.";
  }

  typedef DocsisVersion {
    type enumeration {
      enum docsis10 { value 1; }
      enum docsis11 { value 2; }
      enum docsis20 { value 3; }
    }
    description     
     "Indicates the DOCSIS Radio Frequency specification being
      referenced.
      'docsis10' indicates DOCSIS 1.0.
      'docsis11' indicates DOCSIS 1.1.
      'docsis20' indicates DOCSIS 2.0.";
  }

  typedef DocsisQosVersion {
    type enumeration {
      enum docsis10 { value 1; }
      enum docsis11 { value 2; }
    }
    description     
     "Indicates the referenced quality-of-service
      level.
      'docsis10 refers to DOCSIS 1.0 Class of
      Service queuing services, and 'docsis11' refers
      to DOCSIS 1.1 Quality of Service.";
  }

  typedef DocsisUpstreamType {
    type enumeration {
      enum unknown      { value 0; }
      enum tdma         { value 1; }
      enum atdma        { value 2; }
      enum scdma        { value 3; }
      enum tdmaAndAtdma { value 4; }
    }
    description     
     "Indicates the DOCSIS Upstream Channel Type.
      'unknown' means information not available.
      'tdma' is related to TDMA, Time Division
      Multiple Access; 'atdma' is related to A-TDMA,
      Advanced Time Division Multiple Access,
      'scdma' is related to S-CDMA, Synchronous
      Code Division Multiple Access.
      'tdmaAndAtdma is related to simultaneous support of
      TDMA and A-TDMA modes.";
  }

  typedef DocsEqualizerData {
    type binary {
      length "0 | 36..260";
    }
    description     
     "This data type represents the equalizer data
      as measured at the receiver interface.
      The format of the equalizer follows the structure of the
      Transmit Equalization Adjust RNG-RSP TLV of DOCSIS RFI
      v2.0 :
      1 byte Main tap location 1..(n + m)
      1 byte Number of forward taps per symbol
      1 byte Number of forward taps: n
      1 byte Number of reverse taps: m
      
      Following are the equalizer coefficients:
      First, forward taps coefficients:
      2 bytes F1 (real),  2 bytes  F1 (imag)
      
      
      ...
      2 bytes Fn (real),  2 bytes  Fn (imag)
      
      Then, reverse taps coefficients:
      2 bytes D1 (real),  2 bytes  D1 (imag)
      ...
      
      2 bytes Dm (real),  2 bytes  Dm (imag)
      
      The equalizer coefficients are considered signed 16-bit
      integers in the range from -32768 (0x8000) to 32767
      (0x7FFF).
      
      DOCSIS specifications require up to a maximum of
      64 equalizer taps (n + m); therefore, this object size
       can get up 260 bytes (4 + 4x64).
      The minimum object size (other than zero) for a t-spaced
      tap with a minimum of 8 symbols will be 36 (4 + 4x8).";
    reference       
     "Data-Over-Cable Service Interface Specifications: Radio
      Frequency Interface Specification SP-RFIv2.0-I10-051209,
      Figure 8-23.";
  }

  container docsIfBaseObjects {
      uses docsIfBaseObjectsGroup;
  }

  grouping docsIfBaseObjectsGroup {


    /* XXX table comments here XXX */

    list docsIfDownstreamChannelEntry {

      key "ifIndex";
      description   
       "An entry provides a list of attributes for a single
        downstream channel.
        An entry in this table exists for each ifEntry with an
        ifType of docsCableDownstream(128).";

      leaf ifIndex {
        type int32;
        config false;
        description 
         "Automagically generated keyref leaf.";
      }

      leaf docsIfDownChannelId {
        type int32 {
          range "0..255";
        }
        config false;
        description 
         "The Cable Modem Termination System identification of the
          downstream channel within this particular MAC interface.
          if the interface is down, the object returns the most
          current value.  If the downstream channel ID is unknown,
          this object returns a value of 0.";
      }

      leaf docsIfDownChannelFrequency {
        type int32 {
          range "0..1000000000";
        }
        units "hertz";
        config true;
        description 
         "The center of the downstream frequency associated with
          this channel.  This object will return the current tuner
          
          
          frequency.  If a CMTS provides IF output, this object
          will return 0, unless this CMTS is in control of the
          final downstream frequency.  See the associated
          compliance object for a description of valid frequencies
          that may be written to this object.";
        reference   
         "Data-Over-Cable Service Interface Specifications: Radio
          Frequency Interface Specification SP-RFIv2.0-I10-051209,
          Section 6.3.3.";
      }

      leaf docsIfDownChannelWidth {
        type int32 {
          range "0..16000000";
        }
        units "hertz";
        config true;
        description 
         "The bandwidth of this downstream channel.  Most
          implementations are expected to support a channel width
          of 6 MHz (North America) and/or 8 MHz (Europe).  See the
          associated compliance object for a description of the
          valid channel widths for this object.";
        reference   
         "Data-Over-Cable Service Interface Specifications: Radio
          Frequency Interface Specification SP-RFIv2.0-I10-051209,
          Table 6-17.";
      }

      leaf docsIfDownChannelModulation {
        type enumeration {
          enum unknown { value 1; }
          enum other   { value 2; }
          enum qam64   { value 3; }
          enum qam256  { value 4; }
        }
        config true;
        description 
         "The modulation type associated with this downstream
          channel.  If the interface is down, this object either
          returns the configured value (CMTS), the most current
          value (CM), or the value of unknown(1).  See the
          associated conformance object for write conditions and
          limitations.  See the reference for specifics on the
          modulation profiles implied by qam64 and qam256.";
        reference   
         "Data-Over-Cable Service Interface Specifications: Radio
          
          
          Frequency Interface Specification SP-RFIv2.0-I10-051209,
          Table 6-17.";
      }

      leaf docsIfDownChannelInterleave {
        type enumeration {
          enum unknown           { value 1; }
          enum other             { value 2; }
          enum taps8Increment16  { value 3; }
          enum taps16Increment8  { value 4; }
          enum taps32Increment4  { value 5; }
          enum taps64Increment2  { value 6; }
          enum taps128Increment1 { value 7; }
          enum taps12increment17 { value 8; }
        }
        config true;
        description 
         "The Forward Error Correction (FEC) interleaving used
          for this downstream channel.
          Values are defined as follows:
          taps8Increment16(3):   protection 5.9/4.1 usec,
                                 latency .22/.15 msec
          taps16Increment8(4):   protection 12/8.2 usec,
                                 latency .48/.33 msec
          taps32Increment4(5):   protection 24/16 usec,
                                 latency .98/.68 msec
          taps64Increment2(6):   protection 47/33 usec,
                                 latency 2/1.4 msec
          taps128Increment1(7):  protection 95/66 usec,
                                 latency 4/2.8 msec
          taps12increment17(8):  protection 18/14 usec,
                                 latency 0.43/0.32 msec
          
          The value 'taps12increment17' is supported by EuroDOCSIS
          cable systems only, and the others by DOCSIS cable systems.
          
          If the interface is down, this object either returns
          the configured value (CMTS), the most current value (CM),
          or the value of unknown(1).
          The value of other(2) is returned if the interleave
          is known but not defined in the above list.
          See the associated conformance object for write
          conditions and limitations.  See the reference for the FEC
          configuration described by the setting of this object.";
        reference   
         "Data-Over-Cable Service Interface Specifications: Radio
          Frequency Interface Specification SP-RFIv2.0-I10-051209,
          
          
          Table 6-15.";
      }

      leaf docsIfDownChannelPower {
        type docs-if:TenthdBmV;
        units "dBmV";
        config true;
        description 
         "At the CMTS, the operational transmit power.  At the CM,
          the received power level.
          If the interface is down, this object either returns
          the configured value (CMTS), the most current value (CM)
          or the value of 0.  See the associated conformance object
          for write conditions and limitations.  See the reference
          for recommended and required power levels.";
        reference   
         "Data-Over-Cable Service Interface Specifications: Radio
          Frequency Interface Specification SP-RFIv2.0-I10-051209,
          Tables 6-16, 6-17.";
      }

      leaf docsIfDownChannelAnnex {
        type enumeration {
          enum unknown { value 1; }
          enum other   { value 2; }
          enum annexA  { value 3; }
          enum annexB  { value 4; }
          enum annexC  { value 5; }
        }
        config false;
        description 
         "The value of this object indicates the conformance of
          the implementation to important regional cable standards.
          annexA : Annex A from ITU-T J.83 is used.
                   (equivalent to EN 300 429)
          annexB : Annex B from ITU-T J.83 is used.
          annexC : Annex C from ITU-T J.83 is used.";
        reference   
         "Data-Over-Cable Service Interface Specifications: Radio
          Frequency Interface Specification SP-RFIv2.0-I10-051209,
          Sections 6.3.1, and H.3.1.";
      }

      leaf docsIfDownChannelStorageType {
        type smiv2:StorageType;
        config false;
        description 
         "The storage type for this conceptual row.
          Entries with this object set to permanent(4)
          do not require write operations for read-write
          objects.";
      }
    }


    /* XXX table comments here XXX */

    list docsIfUpstreamChannelEntry {

      key "ifIndex";
      description   
       "List of attributes for a single upstream channel.  For
        DOCSIS 2.0 CMTSs, an entry in this table exists for
        each ifEntry with an ifType of docsCableUpstreamChannel
        (205).
        For DOCSIS 1.x CM/CMTSs and DOCSIS 2.0 CMs, an entry in
        this table exists for each ifEntry with an ifType of
        docsCableUpstream (129).
        
        For DOCSIS 2.0 CMTSs, two classes of interfaces can be
        defined for this table:
         o Upstream Physical Interfaces: The traditional DOCSIS
           1.x CMTS upstream interface ifType 129 and the DOCSIS
           2.0 ifType 205 that are functional.  In other words,
           interfaces that represent upstream receivers within
           an RF MAC interface.
           Entries of physical interfaces are exposed to the
           management interface with their corresponding
           ifStack hierarchy and are not administratively
           created by this table.
        
        
        
         o Upstream Temporary Interfaces: A fictitious
           interface created for the purpose of manipulating
           physical interface parameters offline, then
           validating prior to updating the target physical
           interface.
        
        In case of a reinitialization of the managed system,
        physical interfaces values persist while the temporary
        interfaces are not recreated.
        
        This mechanism helps to minimize service disruptions
        originating in situations where a group of interface
        parameter values need to be consistent with each other
        in SET operations.  A temporary buffer
        (temporary interface) is provided to allow the CMTS
        to validate the parameters offline.";

      leaf ifIndex {
        type int32;
        config false;
        description 
         "Automagically generated keyref leaf.";
      }

      leaf docsIfUpChannelId {
        type int32 {
          range "0..255";
        }
        config false;
        description 
         "The CMTS identification of the upstream channel.";
      }

      leaf docsIfUpChannelFrequency {
        type int32 {
          range "0..1000000000";
        }
        units "hertz";
        config true;
        description 
         "The center of the frequency band associated with this
          upstream interface.  This object returns 0 if the frequency
          is undefined or unknown.  Minimum permitted upstream
          frequency is 5,000,000 Hz for current technology.  See
          the associated conformance object for write conditions
          and limitations.";
        reference   
         "Data-Over-Cable Service Interface Specifications: Radio
          Frequency Interface Specification SP-RFIv2.0-I10-051209,
          Table 4-2.";
      }

      leaf docsIfUpChannelWidth {
        type int32 {
          range "0..64000000";
        }
        units "hertz";
        config true;
        description 
         "The bandwidth of this upstream interface.  This object
          returns 0 if the interface width is undefined or unknown.
          Minimum permitted interface width is currently 200,000 Hz.
          See the associated conformance object for write conditions
          and limitations.";
        reference   
         "Data-Over-Cable Service Interface Specifications: Radio
          Frequency Interface Specification SP-RFIv2.0-I10-051209,
          Table 6-5.";
      }

      leaf docsIfUpChannelModulationProfile {
        type uint32;
        config true;
        description 
         "An entry identical to the docsIfModIndex in the
          docsIfCmtsModulationTable that describes this channel.
          This channel is further instantiated there by a grouping
          of interval usage codes (IUCs) that, together, fully
          describe the channel modulation.  This object returns 0 if
          the docsIfCmtsModulationTable entry does not exist or is
          empty.  See the associated conformance object for write
          conditions and limitations.
          
          
          Setting this object returns an 'inconsistentValue'
          error if the following conditions are not satisfied:
          1. All the IUC entries in the selected modulation profile
          MUST have the same value of docsIfCmtsModChannelType.
          2. All of the Modulation parameters in the selected
          modulation profile MUST be consistent with the other
          parameters in this docsIfUpstreamChannelEntry.";
        reference   
         "Data-Over-Cable Service Interface Specifications: Radio
          Frequency Interface Specification SP-RFIv2.0-I10-051209,
          Table 8-19.";
      }

      leaf docsIfUpChannelSlotSize {
        type uint32;
        units "ticks";
        config true;
        description 
         "Applicable to TDMA and ATDMA channel types only.
          The number of 6.25 microsecond ticks in each upstream
          mini-slot.  Returns zero if the value is undefined or
          unknown or in case of an SCDMA channel.
          See the associated conformance object for write
          conditions and limitations.";
        reference   
         "Data-Over-Cable Service Interface Specifications: Radio
          Frequency Interface Specification SP-RFIv2.0-I10-051209,
          Section 8.1.2.4.";
      }

      leaf docsIfUpChannelTxTimingOffset {
        type uint32;
        config false;
        description 
         "At the CM, a measure of the current round trip time
          obtained from the ranging offset (initial ranging offset +
          ranging offset adjustments).
          At the CMTS, the maximum of timing offset, among all the
          CMs that are/were present on the channel, taking into
          account all ( initial + periodic ) timing offset
          corrections that were sent for each of the CMs.  Generally,
          these measurements are positive, but if the measurements
          are negative, the value of this object is zero.  Used for
          timing of CM upstream transmissions to ensure synchronized
          arrivals at the CMTS.
          Units are one 64th fraction of 6.25 microseconds.";
        reference   
         "Data-Over-Cable Service Interface Specifications: Radio
          Frequency Interface Specification SP-RFIv2.0-I10-051209,
          Section 6.2.19.";
      }

      leaf docsIfUpChannelRangingBackoffStart {
        type int32 {
          range "0..16";
        }
        config true;
        description 
         "The initial random backoff window to use when retrying
          Ranging Requests.  Expressed as a power of 2.  A value of
          16 at the CMTS indicates that a proprietary adaptive retry
          mechanism is to be used.  See the associated conformance
          object for write conditions and limitations.";
        reference   
         "Data-Over-Cable Service Interface Specifications: Radio
          Frequency Interface Specification SP-RFIv2.0-I10-051209,
          Sections 8.3.4, and 9.4.";
      }

      leaf docsIfUpChannelRangingBackoffEnd {
        type int32 {
          range "0..16";
        }
        config true;
        description 
         "The final random backoff window to use when retrying
          Ranging Requests.  Expressed as a power of 2.  A value of
          16 at the CMTS indicates that a proprietary adaptive retry
          mechanism is to be used.  See the associated conformance
          object for write conditions and limitations.";
        reference   
         "Data-Over-Cable Service Interface Specifications: Radio
          Frequency Interface Specification SP-RFIv2.0-I10-051209,
          Section 8.3.4, and 9.4.";
      }

      leaf docsIfUpChannelTxBackoffStart {
        type int32 {
          range "0..16";
        }
        config true;
        description 
         "The initial random backoff window to use when retrying
          transmissions.  Expressed as a power of 2.  A value of 16
          at the CMTS indicates that a proprietary adaptive retry
          mechanism is to be used.  See the associated conformance
          object for write conditions and limitations.";
        reference   
         "Data-Over-Cable Service Interface Specifications: Radio
          Frequency Interface Specification SP-RFIv2.0-I10-051209,
          Section 8.3.4, and 9.4.";
      }

      leaf docsIfUpChannelTxBackoffEnd {
        type int32 {
          range "0..16";
        }
        config true;
        description 
         "The final random backoff window to use when retrying
          transmissions.  Expressed as a power of 2.  A value of 16
          at the CMTS indicates that a proprietary adaptive retry
          mechanism is to be used.  See the associated conformance
          object for write conditions and limitations.";
        reference   
         "Data-Over-Cable Service Interface Specifications: Radio
          Frequency Interface Specification SP-RFIv2.0-I10-051209,
          Section 8.3.4, and 9.4.";
      }

      leaf docsIfUpChannelScdmaActiveCodes {
        type uint32 {
          range "0 | 64..66 | 68..70 | 72 | 74..78 | 80..82 | 84..88 | 90..96 | 98..100 | 102 | 104..106 | 108 | 110..112 | 114..126 | 128";
        }
        config true;
        description 
         "Applicable for SCDMA channel types only.
          Number of active codes.  Returns zero for
          Non-SCDMA channel types.  Note that legal
          values from 64..128 MUST be non-prime.";
        reference   
         "Data-Over-Cable Service Interface Specifications: Radio
          Frequency Interface Specification SP-RFIv2.0-I10-051209,
          Section 6.2.11.2.1.";
      }

      leaf docsIfUpChannelScdmaCodesPerSlot {
        type int32 {
          range "0 | 2..32";
        }
        units "codesperMinislots";
        config true;
        description 
         "Applicable for SCDMA channel types only.
          The number of SCDMA codes per mini-slot.
          Returns zero if the value is undefined or unknown or in
          
          
          case of a TDMA or ATDMA channel.";
        reference   
         "Data-Over-Cable Service Interface Specifications: Radio
          Frequency Interface Specification SP-RFIv2.0-I10-051209,
          Section 6.2.11.2.1.";
      }

      leaf docsIfUpChannelScdmaFrameSize {
        type uint32 {
          range "0..32";
        }
        units "spreadIntervals";
        config true;
        description 
         "Applicable for SCDMA channel types only.
          SCDMA Frame size in units of spreading intervals.
          This value returns zero for non-SCDMA Profiles.";
        reference   
         "Data-Over-Cable Service Interface Specifications: Radio
          Frequency Interface Specification SP-RFIv2.0-I10-051209,
          Section 6.2.12.";
      }

      leaf docsIfUpChannelScdmaHoppingSeed {
        type uint32 {
          range "0..32767";
        }
        config true;
        description 
         "Applicable for SCDMA channel types only.
          15-bit seed used for code hopping sequence initialization.
          Returns zero for non-SCDMA channel types.
          Setting this value to a value different than zero for
          non-SCDMA channel types returns the error 'wrongValue'.";
        reference   
         "Data-Over-Cable Service Interface Specifications: Radio
          Frequency Interface Specification SP-RFIv2.0-I10-051209,
          Section 6.2.14.1.";
      }

      leaf docsIfUpChannelType {
        type docs-if:DocsisUpstreamType;
        config false;
        description 
         "Reflects the Upstream channel type.
          This object returns the value of docsIfCmtsModChannelType
          for the modulation profile selected in
          docsIfUpChannelModulationProfile for this row.";
        reference   
         "Data-Over-Cable Service Interface Specifications: Radio
          Frequency Interface Specification SP-RFIv2.0-I10-051209,
          Section 6.2.1.";
      }

      leaf docsIfUpChannelCloneFrom {
        type if-mib:InterfaceIndexOrZero;
        config true;
        description 
         "This object contains the ifIndex value of the physical
          interface row entry whose parameters are to be adjusted.
          
          Upon setting this object to the ifIndex value of a
          physical interface, the following interface objects values
          are copied to this entry:
          docsIfUpChannelFrequency,
          docsIfUpChannelWidth,
          docsIfUpChannelModulationProfile,
          docsIfUpChannelSlotSize,
          docsIfUpChannelRangingBackoffStart,
          docsIfUpChannelRangingBackoffEnd,
          docsIfUpChannelTxBackoffStart,
          docsIfUpChannelTxBackoffEnd,
          docsIfUpChannelScdmaActiveCodes,
          docsIfUpChannelScdmaCodesPerSlot,
          docsIfUpChannelScdmaFrameSize,
          docsIfUpChannelScdmaHoppingSeed,
          docsIfUpChannelType, and
          docsIfUpChannelPreEqEnable
          Setting this object to the value of a non-existent or
          a temporary upstream interface returns the error
          'wrongValue'.
          This object MUST contain a value of zero for physical
          interfaces entries.
          Setting this object in row entries that correspond to
          physical interfaces returns the error 'wrongValue'.";
      }

      leaf docsIfUpChannelUpdate {
        type smiv2:TruthValue;
        config true;
        description 
         "Used to perform the copy of adjusted parameters from the
          temporary interface entry to the physical interface
          indicated by the docsIfUpChannelCloneFrom object.  The
          transfer is initiated through an SNMP SET to 'true' of
          
          
          this object.
          A SET to 'true' fails and returns error 'commitFailed'
          if docsIfUpChannelStatus value is 'notInService', which
          means that the interface parameters values are not
          compatible with each other or have not been validated yet.
          Reading this object always returns 'false'.";
      }

      leaf docsIfUpChannelStatus {
        type smiv2:RowStatus;
        config true;
        description 
         "This object is only used for the creation of a temporary
          upstream row with the purpose of updating the parameters
          of a physical upstream channel entry.
          
          The following restrictions apply to this object:
          1. This object is not writable for physical interfaces.
          2. Temporary interface entries are only created by a SET
             of this object to createandWait(5).
          3. ifAdminStatus from the Interface MIB RFC 2863 is used
             to take a physical upstream channel offline, to be
             consistent with DOCSIS 1.x operation, as indicated in
             RFC 2670.
             In addition,
              o ifAdminStatus 'down' is reflected in this object
                as 'notInService'.
              o ifOperStatus 'down' while ifAdminStatus 'up' is
                reflected in this object as 'notInservice'.
          4. Temporary created rows MUST be set to 'active' with
             the purpose of validating upstream parameter
             consistency prior to transferring the parameters to the
             physical interface.
          
          Below is a mandatory procedure for adjusting the values
          of a physical interface:
          1. Create a temporary interface entry through an SNMP SET
             using 'createAndWait'.  At this point, the RowStatus
             reports 'notReady'.
             The Manager entity uses an ifIndex value outside the
             operational range of the physical interfaces for the
             creation of a temporary interface.
          2. Set the docsIfUpChannelCloneFrom object to the ifIndex
             value of the physical row to update.  Now
             docsIfUpChannelStatus reports 'notInService'.
          3. Change the upstream parameters to the desired values
             in the temporary row.
          
          
          4. Validate that all parameters are consistent by setting
             docsIfUpChannelStatus to 'active'.  A failure to set the
             RowStatus to 'active' returns the error 'commitFailed',
             which means the parameters are not compatible with the
             target physical interface.
          5. With docsIfUpChannelStatus 'active', transfer the
             parameters to the target physical interface by setting
             the object docsIfUpChannelUpdate to 'true'.
          6. Delete the temporary row by setting
             docsIfUpChannelStatus to 'destroy'.";
      }

      leaf docsIfUpChannelPreEqEnable {
        type smiv2:TruthValue;
        config true;
        description 
         "At the CMTS, this object is used to enable or disable
          pre-equalization on the upstream channel represented by
          this table instance.  At the CM, this object is read-only
          and reflects the status of pre-equalization as represented
          in the RNG-RSP.  Pre-equalization is considered enabled at
          the CM if a RNG-RSP with pre-equalization data has been
          received at least once since the last mac
          reinitialization.";
      }
    }


    /* XXX table comments here XXX */

    list docsIfQosProfileEntry {

      key "docsIfQosProfIndex";
      description   
       "Describes the attributes for a single class of service.
        If implemented as read-create in the Cable Modem
        Termination System, creation of entries in this table is
        controlled by the value of
        docsIfCmtsQosProfilePermissions.
        
        If implemented as read-only, entries are created based
        on information in REG-REQ MAC messages received from
        cable modems (for Cable Modem Termination System), or
        based on information extracted from the TFTP option file
        (for Cable Modem).
        In the Cable Modem Termination System, read-only entries
        are removed if no longer referenced by
        docsIfCmtsServiceTable.
        
        An entry in this table MUST not be removed while it is
        referenced by an entry in docsIfCmServiceTable (Cable
        Modem) or docsIfCmtsServiceTable (Cable Modem Termination
        System).
        
        An entry in this table SHOULD NOT be changeable while
        it is referenced by an entry in docsIfCmtsServiceTable.
        
        If this table is created automatically, there SHOULD only
        be a single entry for each Class of Service.  Multiple
        entries with the same Class of Service parameters are NOT
        RECOMMENDED.";


      leaf docsIfQosProfIndex {
        type int32 {
          range "1..16383";
        }
        config false;
        description 
         "The index value that uniquely identifies an entry
          in the docsIfQosProfileTable.";
      }

      leaf docsIfQosProfPriority {
        type int32 {
          range "0..7";
        }
        config true;
        description 
         "A relative priority assigned to this service when
          allocating bandwidth.  Zero indicates lowest priority
          and seven indicates highest priority.
          Interpretation of priority is device-specific.
          MUST NOT be changed while this row is active.";
        reference   
         "Data-Over-Cable Service Interface Specifications: Radio
          Frequency Interface Specification SP-RFIv2.0-I10-051209,
          Annex C.1.1.4.";
      }

      leaf docsIfQosProfMaxUpBandwidth {
        type int32 {
          range "0..100000000";
        }
        units "bits per second";
        config true;
        description 
         "The maximum upstream bandwidth, in bits per second,
          allowed for a service with this service class.
          Zero if there is no restriction of upstream bandwidth.
          MUST NOT be changed while this row is active.";
        reference   
         "Data-Over-Cable Service Interface Specifications: Radio
          Frequency Interface Specification SP-RFIv2.0-I10-051209,
          Annex C.1.1.4.";
      }

      leaf docsIfQosProfGuarUpBandwidth {
        type int32 {
          range "0..100000000";
        }
        units "bits per second";
        config true;
        description 
         "Minimum guaranteed upstream bandwidth, in bits per second,
          
          
          allowed for a service with this service class.
          MUST NOT be changed while this row is active.";
        reference   
         "Data-Over-Cable Service Interface Specifications: Radio
          Frequency Interface Specification SP-RFIv2.0-I10-051209,
          Annex C.1.1.4.";
      }

      leaf docsIfQosProfMaxDownBandwidth {
        type int32 {
          range "0..100000000";
        }
        units "bits per second";
        config true;
        description 
         "The maximum downstream bandwidth, in bits per second,
          allowed for a service with this service class.
          Zero if there is no restriction of downstream bandwidth.
          MUST NOT be changed while this row is active.";
        reference   
         "Data-Over-Cable Service Interface Specifications: Radio
          Frequency Interface Specification SP-RFIv2.0-I10-051209,
          Annex C.1.1.4.";
      }

      leaf docsIfQosProfMaxTxBurst {
        type int32 {
          range "0..255";
        }
        units "mini-slots";
        config true;
        status deprecated;
        description 
         "The maximum number of mini-slots that may be requested
          for a single upstream transmission.
          A value of zero means there is no limit.
          MUST NOT be changed while this row is active.
          This object has been deprecated and replaced by
          docsIfQosProfMaxTransmitBurst, to fix a mismatch
          of the units and value range with respect to the DOCSIS
          Maximum Upstream Channel Transmit Burst Configuration
          Setting.";
        reference   
         "Data-Over-Cable Service Interface Specifications: Radio
          Frequency Interface Specification SP-RFIv2.0-I10-051209,
          C.1.1.4.";
      }

      leaf docsIfQosProfBaselinePrivacy {
        type smiv2:TruthValue;
        config true;
        description 
         "Indicates whether Baseline Privacy is enabled for this
          service class.
          MUST NOT be changed while this row is active.";
      }

      leaf docsIfQosProfStatus {
        type smiv2:RowStatus;
        config true;
        description 
         "This is object is used to create or delete rows in
          this table.  This object MUST NOT be changed from active
          while the row is referenced by any entry in either
          docsIfCmServiceTable (on the CM) or
          docsIfCmtsServiceTable (on the CMTS).";
      }

      leaf docsIfQosProfMaxTransmitBurst {
        type int32 {
          range "0..65535";
        }
        units "bytes";
        config true;
        description 
         "The maximum number of bytes that may be requested for a
          single upstream transmission.  A value of zero means there
          is no limit.  Note: This value does not include any
          physical layer overhead.
          MUST NOT be changed while this row is active.";
        reference   
         "Data-Over-Cable Service Interface Specifications: Radio
          Frequency Interface Specification SP-RFIv2.0-I10-051209,
          Annex C.1.1.4.";
      }

      leaf docsIfQosProfStorageType {
        type smiv2:StorageType;
        config false;
        description 
         "The storage type for this conceptual row.
          Entries with this object set to permanent(4)
          
          
          do not require write operations for writable
          objects.";
      }
    }


    /* XXX table comments here XXX */

    list docsIfSignalQualityEntry {

      key "ifIndex";
      description   
       "At the CM, this object describes the PHY characteristics of
        a downstream channel.  At the CMTS, it describes the PHY
        signal quality of an upstream channel.
        An entry in this table exists for each ifEntry with an
        ifType of docsCableDownstream(128) for Cable Modems.
        For DOCSIS 1.1 Cable Modem Termination Systems, an entry
        exists for each ifEntry with an ifType of
        docsCableUpstream (129).
        For DOCSIS 2.0 Cable Modem Termination Systems, an entry
        exists for each ifEntry with an ifType of
        docsCableUpstreamChannel (205).";

      leaf ifIndex {
        type int32;
        config false;
        description 
         "Automagically generated keyref leaf.";
      }

      leaf docsIfSigQIncludesContention {
        type smiv2:TruthValue;
        config false;
        description 
         "true(1) if this CMTS includes contention intervals in
          the counters in this table.  Always false(2) for CMs.";
        reference   
         "Data-Over-Cable Service Interface Specifications: Radio
          Frequency Interface Specification SP-RFIv2.0-I10-051209,
          Section 9.4.1";
      }

      leaf docsIfSigQUnerroreds {
        type yang:counter32;
        units "codewords";
        config false;
        description 
         "Codewords received on this channel without error.
          This includes all codewords, whether or not they
          were part of frames destined for this device.
          Discontinuities in the value of this counter can occur
          at reinitialization of the managed system, and at other
          times as indicated by the value of
          ifCounterDiscontinuityTime for the associated ifIndex.";
        reference   
         "Data-Over-Cable Service Interface Specifications: Radio
          Frequency Interface Specification SP-RFIv2.0-I10-051209,
          Sections 6.2.4, and 6.3.6.";
      }

      leaf docsIfSigQCorrecteds {
        type yang:counter32;
        units "codewords";
        config false;
        description 
         "Codewords received on this channel with correctable
          errors.  This includes all codewords, whether or not
          they were part of frames destined for this device.
          Discontinuities in the value of this counter can occur
          at reinitialization of the managed system, and at other
          times as indicated by the value of
          ifCounterDiscontinuityTime for the associated ifIndex.";
        reference   
         "Data-Over-Cable Service Interface Specifications: Radio
          Frequency Interface Specification SP-RFIv2.0-I10-051209,
          Sections 6.2.4, and 6.3.6.";
      }

      leaf docsIfSigQUncorrectables {
        type yang:counter32;
        units "codewords";
        config false;
        description 
         "Codewords received on this channel with uncorrectable
          errors.  This includes all codewords, whether or not
          they were part of frames destined for this device.
          Discontinuities in the value of this counter can occur
          at reinitialization of the managed system, and at other
          times as indicated by the value of
          ifCounterDiscontinuityTime for the associated ifIndex.";
        reference   
         "Data-Over-Cable Service Interface Specifications: Radio
          Frequency Interface Specification SP-RFIv2.0-I10-051209,
          Sections 6.2.4, and 6.3.6.";
      }

      leaf docsIfSigQSignalNoise {
        type docs-if:TenthdB;
        units "TenthdB";
        config false;
        description 
         "Signal/Noise ratio as perceived for this channel.
          At the CM, this object  describes the Signal/Noise of the
          downstream channel.  At the CMTS, it describes the
          average Signal/Noise of the upstream channel.";
        reference   
         "Data-Over-Cable Service Interface Specifications: Radio
          Frequency Interface Specification SP-RFIv2.0-I10-051209,
          Tables 4-1 and 4-2";
      }

      leaf docsIfSigQMicroreflections {
        type int32 {
          range "0..255";
        }
        units "-dBc";
        config false;
        description 
         "Microreflections, including in-channel response
          as perceived on this interface, measured in dBc below
          the signal level.
          This object is not assumed to return an absolutely
          accurate value, but it gives a rough indication
          
          
          of microreflections received on this interface.
          It is up to the implementer to provide information
          as accurately as possible.";
        reference   
         "Data-Over-Cable Service Interface Specifications: Radio
          Frequency Interface Specification SP-RFIv2.0-I10-051209,
          Tables 4-1 and 4-2";
      }

      leaf docsIfSigQEqualizationData {
        type docs-if:DocsEqualizerData;
        config false;
        description 
         "At the CM, this object returns the equalization data for
          the downstream channel.
          
          At the CMTS, this object is not applicable and is not
          instantiated.  Note that previous CMTS implementations
          may instantiate this object in two ways:
          - An equalization value indicating an equalization
            average for the upstream channel.  Those values have
            vendor-dependent interpretations.
          - Return a zero-length OCTET STRING to indicate that
            the value is unknown or if there is no equalization
            data available or defined.";
        reference   
         "DOCSIS Radio Frequency Interface Specification,
          Figure 6-23.";
      }

      leaf docsIfSigQExtUnerroreds {
        type yang:counter64;
        units "codewords";
        config false;
        description 
         "Codewords received on this channel without error.
          This includes all codewords, whether or not they
          were part of frames destined for this device.
          This is the 64-bit version of docsIfSigQUnerroreds.
          Discontinuities in the value of this counter can occur
          at reinitialization of the managed system, and at other
          times as indicated by the value of
          ifCounterDiscontinuityTime for the associated ifIndex.";
        reference   
         "Data-Over-Cable Service Interface Specifications: Radio
          
          
          Frequency Interface Specification SP-RFIv2.0-I10-051209,
          Sections 6.2.4, and 6.3.6.";
      }

      leaf docsIfSigQExtCorrecteds {
        type yang:counter64;
        units "codewords";
        config false;
        description 
         "Codewords received on this channel with correctable
          errors.  This includes all codewords, whether or not
          they were part of frames destined for this device.
          This is the 64-bit version of docsIfSigQCorrecteds.
          Discontinuities in the value of this counter can occur
          at reinitialization of the managed system, and at other
          times as indicated by the value of
          ifCounterDiscontinuityTime for the associated ifIndex.";
        reference   
         "Data-Over-Cable Service Interface Specifications: Radio
          Frequency Interface Specification SP-RFIv2.0-I10-051209,
          Sections 6.2.4, and 6.3.6.";
      }

      leaf docsIfSigQExtUncorrectables {
        type yang:counter64;
        units "codewords";
        config false;
        description 
         "Codewords received on this channel with uncorrectable
          errors.  This includes all codewords, whether or not
          they were part of frames destined for this device.
          This is the 64-bit version of docsIfSigQUncorrectables.
          Discontinuities in the value of this counter can occur
          at reinitialization of the managed system, and at other
          times as indicated by the value of
          ifCounterDiscontinuityTime for the associated ifIndex.";
        reference   
         "Data-Over-Cable Service Interface Specifications: Radio
          Frequency Interface Specification SP-RFIv2.0-I10-051209,
          Sections 6.2.4, 6.3.6.";
      }
    }

    leaf docsIfDocsisBaseCapability {
      type docs-if:DocsisVersion;
      config false;
      description   
       "Indication of the DOCSIS capability of the device.";
      reference     
       "Data-Over-Cable Service Interface Specifications: Radio
        Frequency Interface Specification SP-RFIv2.0-I10-051209,
        Annex G.";
    }
  }

  container docsIfCmObjects {
    uses docsIfCmObjectsGroup;
  }

  grouping docsIfCmObjectsGroup {


    /* XXX table comments here XXX */

    list docsIfCmMacEntry {

      key "ifIndex";
      description   
       "An entry containing objects describing attributes of
        each MAC entry, extending the information in ifEntry.
        An entry in this table exists for each ifEntry with an
        ifType of docsCableMaclayer(127).";

      leaf ifIndex {
        type int32;
        config false;
        description 
         "Automagically generated keyref leaf.";
      }

      leaf docsIfCmCmtsAddress {
        type ieee:mac-address;
        config false;
        description 
         "Identifies the CMTS that is believed to control this MAC
          domain.  At the CM, this will be the source address from
          SYNC, MAP, and other MAC-layer messages.  If the CMTS is
          unknown, returns 00-00-00-00-00-00.";
        reference   
         "Data-Over-Cable Service Interface Specifications: Radio
          Frequency Interface Specification SP-RFIv2.0-I10-051209,
          Section 8.2.2.";
      }

      leaf docsIfCmCapabilities {
        type bits {
          bit atmCells      { position 0; }
          bit concatenation { position 1; }
        }
        config false;
        description 
         "Identifies the capabilities of the MAC implementation
          at this interface.  Note that packet transmission is
          always supported.  Therefore, there is no specific bit
          required to explicitly indicate this capability.
          Note that BITS objects are encoded most significant bit
          first.  For example, if bit 1 is set, the value of this
          object is the octet string '40'H.";
      }

      leaf docsIfCmRangingRespTimeout {
        type yang:timeticks;
        config true;
        status obsolete;
        description
         "Waiting time for a Ranging Response packet.
          This object has been obsoleted and replaced by
          docsIfCmRangingTimeout to correct the typing to
          TimeInterval.";
        reference
         "Data-Over-Cable Service Interface Specifications: Radio
          Frequency Interface Specification SP-RFIv2.0-I10-051209,
          Section 9.1.6.";
      }

      leaf docsIfCmRangingTimeout {
        type smiv2:TimeInterval;
        units "HundredOfSeconds";
        config true;
        description 
         "Waiting time for a Ranging Response packet.
          This object MUST NOT persist at reinitialization
          of the managed system.";
        reference   
         "Data-Over-Cable Service Interface Specifications: Radio
          Frequency Interface Specification SP-RFIv2.0-I10-051209,
          Section 9.1.6, timer T3.";
      }
    }


    /* XXX table comments here XXX */

    list docsIfCmStatusEntry {

      key "ifIndex";
      description   
       "A set of status objects and counters for a single MAC
        layer instance in Cable Modem.
        An entry in this table exists for each ifEntry with an
        ifType of docsCableMaclayer(127).";

      leaf ifIndex {
        type int32;
        config false;
        description 
         "Automagically generated keyref leaf.";
      }

      leaf docsIfCmStatusValue {
        type enumeration {
          enum other                 { value 1; }
          enum notReady              { value 2; }
          enum notSynchronized       { value 3; }
          enum phySynchronized       { value 4; }
          enum usParametersAcquired  { value 5; }
          enum rangingComplete       { value 6; }
          enum ipComplete            { value 7; }
          enum todEstablished        { value 8; }
          enum securityEstablished   { value 9; }
          enum paramTransferComplete { value 10; }
          enum registrationComplete  { value 11; }
          enum operational           { value 12; }
          enum accessDenied          { value 13; }
        }
        config false;
        description 
         "Current Cable Modem connectivity state, as specified
          in the RF Interface Specification.  Interpretations for
          state values 1-12 are clearly outlined in the SP-RFI
          reference given below.
          The state value accessDenied(13) indicates the CMTS has
          sent a Registration Aborted message to the CM.  The same
          state is reported as accessDenied(7) by the CMTS object
          docsIfCmtsCmStatusValue.";
        reference   
         "Data-Over-Cable Service Interface Specifications: Radio
          Frequency Interface Specification SP-RFIv2.0-I10-051209,
          Section 11.2.
          Data-Over-Cable Service Interface Specifications:
          
          
          Operations Support System Interface Specification
          SP-OSSIv2.0-I09-050812, Section 6.3.4.2.";
      }

      leaf docsIfCmStatusCode {
        type binary {
          length "0 | 5..6";
        }
        config false;
        description 
         "Status code for a Cable Modem as defined in the
          OSSI Specification.  The status code consists
          of a single character indicating error groups, followed
          by a two- or three-digit number indicating the status
          condition, followed by a decimal.
          An example of a returned value could be 'T101.0'.
          The zero-length OCTET STRING indicates no status code yet
          registered.";
        reference   
         "Data-Over-Cable Service Interface Specifications:
          Operations Support System Interface Specification
          SP-OSSIv2.0-I09-050812, Annex D.";
      }

      leaf docsIfCmStatusTxPower {
        type docs-if:TenthdBmV;
        units "TenthdBmV";
        config false;
        description 
         "The operational transmit power for the attached upstream
          channel.";
        reference   
         "Data-Over-Cable Service Interface Specifications: Radio
          Frequency Interface Specification SP-RFIv2.0-I10-051209,
          Section 6.2.18.";
      }

      leaf docsIfCmStatusResets {
        type yang:counter32;
        units "resets";
        config false;
        description 
         "Number of times the CM reset or initialized this
          interface.
          Discontinuities in the value of this counter can occur
          at reinitialization of the managed system, and at other
          
          
          times as indicated by the value of
          ifCounterDiscontinuityTime for the associated ifIndex.";
      }

      leaf docsIfCmStatusLostSyncs {
        type yang:counter32;
        config false;
        description 
         "Number of times the CM lost synchronization with
          the downstream channel.
          Discontinuities in the value of this counter can occur
          at reinitialization of the managed system, and at other
          times as indicated by the value of
          ifCounterDiscontinuityTime for the associated ifIndex.";
        reference   
         "Data-Over-Cable Service Interface Specifications: Radio
          Frequency Interface Specification SP-RFIv2.0-I10-051209,
          Section 8.3.2.";
      }

      leaf docsIfCmStatusInvalidMaps {
        type yang:counter32;
        units "maps";
        config false;
        description 
         "Number of times the CM received invalid MAP messages.
          Discontinuities in the value of this counter can occur
          at reinitialization of the managed system, and at other
          times as indicated by the value of
          ifCounterDiscontinuityTime for the associated ifIndex.";
        reference   
         "Data-Over-Cable Service Interface Specifications: Radio
          Frequency Interface Specification SP-RFIv2.0-I10-051209,
          Section 8.3.4.";
      }

      leaf docsIfCmStatusInvalidUcds {
        type yang:counter32;
        units "messages";
        config false;
        description 
         "Number of times the CM received invalid UCD messages.
          Discontinuities in the value of this counter can occur
          at reinitialization of the managed system, and at other
          times as indicated by the value of
          
          
          ifCounterDiscontinuityTime for the associated ifIndex.";
        reference   
         "Data-Over-Cable Service Interface Specifications: Radio
          Frequency Interface Specification SP-RFIv2.0-I10-051209,
          Section 8.3.3.";
      }

      leaf docsIfCmStatusInvalidRangingResponses {
        type yang:counter32;
        units "messages";
        config false;
        description 
         "Number of times the CM received invalid ranging response
          messages.
          Discontinuities in the value of this counter can occur
          at reinitialization of the managed system, and at other
          times as indicated by the value of
          ifCounterDiscontinuityTime for the associated ifIndex.";
        reference   
         "Data-Over-Cable Service Interface Specifications: Radio
          Frequency Interface Specification SP-RFIv2.0-I10-051209,
          Section 8.3.6.";
      }

      leaf docsIfCmStatusInvalidRegistrationResponses {
        type yang:counter32;
        units "messages";
        config false;
        description 
         "Number of times the CM received invalid registration
          response messages.
          Discontinuities in the value of this counter can occur
          at reinitialization of the managed system, and at other
          times as indicated by the value of
          ifCounterDiscontinuityTime for the associated ifIndex.";
        reference   
         "Data-Over-Cable Service Interface Specifications: Radio
          Frequency Interface Specification SP-RFIv2.0-I10-051209,
          Section 8.3.8.";
      }

      leaf docsIfCmStatusT1Timeouts {
        type yang:counter32;
        units "timeouts";
        config false;
        description 
         "Number of times counter T1 expired in the CM.
          Discontinuities in the value of this counter can occur
          at reinitialization of the managed system, and at other
          times as indicated by the value of
          ifCounterDiscontinuityTime for the associated ifIndex.";
        reference   
         "Data-Over-Cable Service Interface Specifications: Radio
          Frequency Interface Specification SP-RFIv2.0-I10-051209,
          Figure 9-2.";
      }

      leaf docsIfCmStatusT2Timeouts {
        type yang:counter32;
        units "timeouts";
        config false;
        description 
         "Number of times counter T2 expired in the CM.
          Discontinuities in the value of this counter can occur
          at reinitialization of the managed system, and at other
          times as indicated by the value of
          ifCounterDiscontinuityTime for the associated ifIndex.";
        reference   
         "Data-Over-Cable Service Interface Specifications: Radio
          Frequency Interface Specification SP-RFIv2.0-I10-051209,
          Figure 9-2.";
      }

      leaf docsIfCmStatusT3Timeouts {
        type yang:counter32;
        units "timeouts";
        config false;
        description 
         "Number of times counter T3 expired in the CM.
          Discontinuities in the value of this counter can occur
          at reinitialization of the managed system, and at other
          times as indicated by the value of
          ifCounterDiscontinuityTime for the associated ifIndex.";
        reference   
         "Data-Over-Cable Service Interface Specifications: Radio
          Frequency Interface Specification SP-RFIv2.0-I10-051209,
          Figure 9-2.";
      }

      leaf docsIfCmStatusT4Timeouts {
        type yang:counter32;
        units "timeouts";
        config false;
        description 
         "Number of times counter T4 expired in the CM.
          Discontinuities in the value of this counter can occur
          at reinitialization of the managed system, and at other
          times as indicated by the value of
          ifCounterDiscontinuityTime for the associated ifIndex.";
        reference   
         "Data-Over-Cable Service Interface Specifications: Radio
          Frequency Interface Specification SP-RFIv2.0-I10-051209,
          Figure 9-2.";
      }

      leaf docsIfCmStatusRangingAborteds {
        type yang:counter32;
        units "attempts";
        config false;
        description 
         "Number of times the ranging process was aborted
          by the CMTS.
          Discontinuities in the value of this counter can occur
          at reinitialization of the managed system, and at other
          times as indicated by the value of
          ifCounterDiscontinuityTime for the associated ifIndex.";
        reference   
         "Data-Over-Cable Service Interface Specifications: Radio
          Frequency Interface Specification SP-RFIv2.0-I10-051209,
          Section 9.3.3.";
      }

      leaf docsIfCmStatusDocsisOperMode {
        type docs-if:DocsisQosVersion;
        config false;
        description 
         "Indication of whether the device has registered using 1.0
          Class of Service or 1.1 Quality of Service.
          An unregistered CM SHOULD indicate 'docsis11' for a
          docsIfDocsisBaseCapability value of DOCSIS 1.1/2.0.  An
          unregistered CM SHOULD indicate 'docsis10'  for a
          docsIfDocsisBaseCapability value of DOCSIS 1.0.";
        reference   
         "Data-Over-Cable Service Interface Specifications: Radio
          Frequency Interface Specification SP-RFIv2.0-I10-051209,
          Annex G.";
      }

      leaf docsIfCmStatusModulationType {
        type docs-if:DocsisUpstreamType;
        config false;
        description 
         "Indicates modulation type status currently used by the
          CM.  Since this object specifically identifies PHY mode,
          the shared upstream channel type is not permitted.";
        reference   
         "Data-Over-Cable Service Interface Specifications: Radio
          Frequency Interface Specification SP-RFIv2.0-I10-051209,
          Section 6.2.1.";
      }

      leaf docsIfCmStatusEqualizationData {
        type docs-if:DocsEqualizerData;
        config false;
        description 
         "Pre-equalization data for this CM after convolution with
          data indicated in the RNG-RSP.  This data is valid when
          docsIfUpChannelPreEqEnable is set to true.";
        reference   
         "Data-Over-Cable Service Interface Specifications: Radio
          Frequency Interface Specification SP-RFIv2.0-I10-051209,
          Figure 8-23.";
      }

      leaf docsIfCmStatusUCCs {
        type yang:counter32;
        units "attempts";
        config false;
        description 
         "The number of successful Upstream Channel Change
          transactions.
          Discontinuities in the value of this counter can occur
          at reinitialization of the managed system, and at other
          times as indicated by the value of
          ifCounterDiscontinuityTime for the associated ifIndex.";
      }

      leaf docsIfCmStatusUCCFails {
        type yang:counter32;
        units "attempts";
        config false;
        description 
         "The number of failed Upstream Channel Change
          transactions.
          Discontinuities in the value of this counter can occur
          at reinitialization of the managed system, and at other
          times as indicated by the value of
          ifCounterDiscontinuityTime for the associated ifIndex.";
      }
    }


    /* XXX table comments here XXX */

    list docsIfCmServiceEntry {

      key "ifIndex docsIfCmServiceId";
      description   
       "Describes the attributes of an upstream bandwidth service
        queue.
        An entry in this table exists for each Service ID.
        The primary index is an ifIndex with an ifType of
        docsCableMaclayer(127).";

      leaf ifIndex {
        type int32;
        config false;
        description 
         "Automagically generated keyref leaf.";
      }

      leaf docsIfCmServiceId {
        type int32 {
          range "1..16383";
        }
        config false;
        description 
         "Identifies a service queue for upstream bandwidth.  The
          attributes of this service queue are shared between the
          CM and the CMTS.  The CMTS allocates upstream bandwidth
          to this service queue based on requests from the CM and
          on the class of service associated with this queue.";
      }

      leaf docsIfCmServiceQosProfile {
        type int32 {
          range "0..16383";
        }
        config false;
        description 
         "The index in docsIfQosProfileTable describing the quality
          of service attributes associated with this particular
          service.  If no associated entry in docsIfQosProfileTable
          exists, this object returns a value of zero.";
      }

      leaf docsIfCmServiceTxSlotsImmed {
        type yang:counter32;
        units "mini-slots";
        config false;
        description 
         "The number of upstream mini-slots that have been used to
          transmit data PDUs in immediate (contention) mode.  This
          includes only those PDUs that are presumed to have
          arrived at the head-end (i.e., those that were explicitly
          acknowledged).  It does not include retransmission attempts
          or mini-slots used by requests.
          Discontinuities in the value of this counter can occur
          at reinitialization of the managed system, and at other
          times as indicated by the value of
          ifCounterDiscontinuityTime for the associated ifIndex.";
        reference   
         "Data-Over-Cable Service Interface Specifications: Radio
          Frequency Interface Specification SP-RFIv2.0-I10-051209,
          Section 9.4.";
      }

      leaf docsIfCmServiceTxSlotsDed {
        type yang:counter32;
        units "mini-slots";
        config false;
        description 
         "The number of upstream mini-slots that have been used to
          transmit data PDUs in dedicated mode (i.e., as a result
          of a unicast Data Grant).
          Discontinuities in the value of this counter can occur
          at reinitialization of the managed system, and at other
          times as indicated by the value of
          ifCounterDiscontinuityTime for the associated ifIndex.";
        reference   
         "Data-Over-Cable Service Interface Specifications: Radio
          Frequency Interface Specification SP-RFIv2.0-I10-051209,
          Section 9.4.";
      }

      leaf docsIfCmServiceTxRetries {
        type yang:counter32;
        units "attempts";
        config false;
        description 
         "The number of attempts to transmit data PDUs containing
          requests for acknowledgment that did not result in
          acknowledgment.
          Discontinuities in the value of this counter can occur
          at reinitialization of the managed system, and at other
          times as indicated by the value of
          ifCounterDiscontinuityTime for the associated ifIndex.";
        reference   
         "Data-Over-Cable Service Interface Specifications: Radio
          Frequency Interface Specification SP-RFIv2.0-I10-051209,
          Section 9.4.";
      }

      leaf docsIfCmServiceTxExceededs {
        type yang:counter32;
        units "attempts";
        config false;
        description 
         "The number of data PDU transmission failures due to
          excessive retries without acknowledgment.
          Discontinuities in the value of this counter can occur
          at reinitialization of the managed system, and at other
          times as indicated by the value of
          
          
          ifCounterDiscontinuityTime for the associated ifIndex.";
        reference   
         "Data-Over-Cable Service Interface Specifications: Radio
          Frequency Interface Specification SP-RFIv2.0-I10-051209,
          Section 9.4.";
      }

      leaf docsIfCmServiceRqRetries {
        type yang:counter32;
        units "attempts";
        config false;
        description 
         "The number of attempts to transmit bandwidth requests
          that did not result in acknowledgment.
          Discontinuities in the value of this counter can occur
          at reinitialization of the managed system, and at other
          times as indicated by the value of
          ifCounterDiscontinuityTime for the associated ifIndex.";
        reference   
         "Data-Over-Cable Service Interface Specifications: Radio
          Frequency Interface Specification SP-RFIv2.0-I10-051209,
          Section 9.4.";
      }

      leaf docsIfCmServiceRqExceededs {
        type yang:counter32;
        units "attempts";
        config false;
        description 
         "The number of requests for bandwidth that failed due to
          excessive retries without acknowledgment.
          Discontinuities in the value of this counter can occur
          at reinitialization of the managed system, and at other
          times as indicated by the value of
          ifCounterDiscontinuityTime for the associated ifIndex.";
        reference   
         "Data-Over-Cable Service Interface Specifications: Radio
          Frequency Interface Specification SP-RFIv2.0-I10-051209,
          Section 9.4.";
      }

      leaf docsIfCmServiceExtTxSlotsImmed {
        type yang:counter64;
        units "mini-slots";
        config false;
        description 
         "The number of upstream mini-slots that have been used to
          transmit data PDUs in immediate (contention) mode.  This
          includes only those PDUs that are presumed to have
          arrived at the head-end (i.e., those that were explicitly
          acknowledged).  It does not include retransmission attempts
          or mini-slots used by requests.
          Discontinuities in the value of this counter can occur
          at reinitialization of the managed system, and at other
          times as indicated by the value of
          ifCounterDiscontinuityTime for the associated ifIndex.";
        reference   
         "Data-Over-Cable Service Interface Specifications: Radio
          Frequency Interface Specification SP-RFIv2.0-I10-051209,
          Section 9.4.";
      }

      leaf docsIfCmServiceExtTxSlotsDed {
        type yang:counter64;
        units "mini-slots";
        config false;
        description 
         "The number of upstream mini-slots that have been used to
          transmit data PDUs in dedicated mode (i.e., as a result
          of a unicast Data Grant).
          Discontinuities in the value of this counter can occur
          at reinitialization of the managed system, and at other
          times as indicated by the value of
          ifCounterDiscontinuityTime for the associated ifIndex.";
        reference   
         "Data-Over-Cable Service Interface Specifications: Radio
          Frequency Interface Specification SP-RFIv2.0-I10-051209,
          Section 9.4.";
      }
    }
  }

  container docsIfCmtsObjects {
    uses docsIfCmtsObjectsGroup;
  }

  grouping docsIfCmtsObjectsGroup {


    /* XXX table comments here XXX */

    list docsIfCmtsMacEntry {

      key "ifIndex";
      description   
       "An entry containing objects describing attributes of each
        MAC entry, extending the information in ifEntry.
        An entry in this table exists for each ifEntry with an
        ifType of docsCableMaclayer(127).";

      leaf ifIndex {
        type int32;
        config false;
        description 
         "Automagically generated keyref leaf.";
      }

      leaf docsIfCmtsCapabilities {
        type bits {
          bit atmCells      { position 0; }
          bit concatenation { position 1; }
        }
        config false;
        description 
         "Identifies the capabilities of the CMTS MAC
          implementation at this interface.  Note that packet
          transmission is always supported.  Therefore, there
          is no specific bit required to explicitly indicate
          this capability.
          Note that BITS objects are encoded most significant bit
          first.  For example, if bit 1 is set, the value of this
          object is the octet string '40'H.";
      }

      leaf docsIfCmtsSyncInterval {
        type int32 {
          range "1..200";
        }
        units "Milliseconds";
        config true;
        description 
         "The interval between CMTS transmission of successive SYNC
          messages at this interface.";
        reference   
         "Data-Over-Cable Service Interface Specifications: Radio
          Frequency Interface Specification SP-RFIv2.0-I10-051209,
          Section 9.3.";
      }

      leaf docsIfCmtsUcdInterval {
        type int32 {
          range "1..2000";
        }
        units "Milliseconds";
        config true;
        description 
         "The interval between CMTS transmission of successive
          Upstream Channel Descriptor messages for each upstream
          channel at this interface.";
        reference   
         "Data-Over-Cable Service Interface Specifications: Radio
          Frequency Interface Specification SP-RFIv2.0-I10-051209,
          Section 9.3";
      }

      leaf docsIfCmtsMaxServiceIds {
        type int32 {
          range "1..16383";
        }
        units "SIDs";
        config false;
        description 
         "The maximum number of service IDs that may be
          simultaneously active.";
      }

      leaf docsIfCmtsInsertionInterval {
        type yang:timeticks;
        config true;
        status obsolete;
        description
         "The amount of time to elapse between each broadcast
          initial maintenance grant.  Broadcast initial maintenance
          grants are used to allow new cable modems to join the
          network.  Zero indicates that a vendor-specific algorithm
          is used instead of a fixed time.  The maximum amount of


          time permitted by the specification is 2 seconds.
          This object has been obsoleted and replaced by
          docsIfCmtsInsertInterval to fix a SYNTAX typing problem.";
        reference
         "Data-Over-Cable Service Interface Specifications: Radio
          Frequency Interface Specification SP-RFIv2.0-I10-051209,
          Annex B.";
      }

      leaf docsIfCmtsInvitedRangingAttempts {
        type int32 {
          range "0..1024";
        }
        units "attempts";
        config true;
        description 
         "The maximum number of attempts to make on invitations
          for ranging requests.  A value of zero means the system
          SHOULD attempt to range forever.";
        reference   
         "Data-Over-Cable Service Interface Specifications: Radio
          Frequency Interface Specification SP-RFIv2.0-I10-051209,
          Section 9.3.3 and Annex B.";
      }

      leaf docsIfCmtsInsertInterval {
        type smiv2:TimeInterval;
        units "HundredOfSeconds";
        config true;
        description 
         "The amount of time to elapse between each broadcast
          initial maintenance grant.  Broadcast initial maintenance
          grants are used to allow new cable modems to join the
          network.  Zero indicates that a vendor-specific algorithm
          is used instead of a fixed time.  The maximum amount of
          time permitted by the specification is 2 seconds.";
        reference   
         "Data-Over-Cable Service Interface Specifications: Radio
          Frequency Interface Specification SP-RFIv2.0-I10-051209,
          Annex B.";
      }

      leaf docsIfCmtsMacStorageType {
        type smiv2:StorageType;
        config false;
        description 
         "The storage type for this conceptual row.
          
          
          Entries with this object set to permanent(4)
          do not require write operations for read-write
          objects.";
      }
    }


    /* XXX table comments here XXX */

    list docsIfCmtsStatusEntry {

      key "ifIndex";
      description   
       "Status entry for a single MAC layer.
        An entry in this table exists for each ifEntry with an
        ifType of docsCableMaclayer(127).";

      leaf ifIndex {
        type int32;
        config false;
        description 
         "Automagically generated keyref leaf.";
      }

      leaf docsIfCmtsStatusInvalidRangeReqs {
        type yang:counter32;
        units "messages";
        config false;
        description 
         "This object counts invalid RNG-REQ messages received on
          this interface.
          Discontinuities in the value of this counter can occur
          
          
          at reinitialization of the managed system, and at other
          times as indicated by the value of
          ifCounterDiscontinuityTime for the associated ifIndex.";
        reference   
         "Data-Over-Cable Service Interface Specifications: Radio
          Frequency Interface Specification SP-RFIv2.0-I10-051209,
          Section 8.3.5.";
      }

      leaf docsIfCmtsStatusRangingAborteds {
        type yang:counter32;
        units "attempts";
        config false;
        description 
         "This object counts ranging attempts that were explicitly
          aborted by the CMTS.
          Discontinuities in the value of this counter can occur
          at reinitialization of the managed system, and at other
          times as indicated by the value of
          ifCounterDiscontinuityTime for the associated ifIndex.";
        reference   
         "Data-Over-Cable Service Interface Specifications: Radio
          Frequency Interface Specification SP-RFIv2.0-I10-051209,
          Section 8.3.6.";
      }

      leaf docsIfCmtsStatusInvalidRegReqs {
        type yang:counter32;
        units "messages";
        config false;
        description 
         "This object counts invalid REG-REQ messages received on
          this interface; that is, syntax, out of range parameters,
          or erroneous requests.
          Discontinuities in the value of this counter can occur
          at reinitialization of the managed system, and at other
          times as indicated by the value of
          ifCounterDiscontinuityTime for the associated ifIndex.";
        reference   
         "Data-Over-Cable Service Interface Specifications: Radio
          Frequency Interface Specification SP-RFIv2.0-I10-051209,
          Section 8.3.7.";
      }

      leaf docsIfCmtsStatusFailedRegReqs {
        type yang:counter32;
        units "attempts";
        config false;
        description 
         "This object counts failed registration attempts.  Included
          are docsIfCmtsStatusInvalidRegReqs, authentication, and
          class of service failures.
          Discontinuities in the value of this counter can occur
          at reinitialization of the managed system, and at other
          times as indicated by the value of
          ifCounterDiscontinuityTime for the associated ifIndex.";
        reference   
         "Data-Over-Cable Service Interface Specifications: Radio
          Frequency Interface Specification SP-RFIv2.0-I10-051209,
          Section 8.3.7.";
      }

      leaf docsIfCmtsStatusInvalidDataReqs {
        type yang:counter32;
        units "messages";
        config false;
        description 
         "This object counts invalid data request messages
          received on this interface.
          Discontinuities in the value of this counter can occur
          at reinitialization of the managed system, and at other
          times as indicated by the value of
          ifCounterDiscontinuityTime for the associated ifIndex.";
      }

      leaf docsIfCmtsStatusT5Timeouts {
        type yang:counter32;
        units "timeouts";
        config false;
        description 
         "This object counts the number of times counter T5
          expired on this interface.
          Discontinuities in the value of this counter can occur
          at reinitialization of the managed system, and at other
          times as indicated by the value of
          ifCounterDiscontinuityTime for the associated ifIndex.";
        reference   
         "Data-Over-Cable Service Interface Specifications: Radio
          Frequency Interface Specification SP-RFIv2.0-I10-051209,
          Figure 9-2.";
      }
    }


    /* XXX table comments here XXX */

    list docsIfCmtsCmStatusEntry {

      key "docsIfCmtsCmStatusIndex";
      description   
       "Status information for a single cable modem.
        An entry in this table exists for each cable modem
        that is connected to the CMTS implementing this table.";


      leaf docsIfCmtsCmStatusIndex {
        type int32 {
          range "1..2147483647";
        }
        config false;
        description 
         "Index value to uniquely identify an entry in this table.
          For an individual cable modem, this index value SHOULD
          NOT change during CMTS uptime.";
      }

      leaf docsIfCmtsCmStatusMacAddress {
        type ieee:mac-address;
        config false;
        description 
         "MAC address of the cable modem.  If the cable modem has
          multiple MAC addresses, this is the MAC address associated
          with the Cable interface.";
        reference   
         "Data-Over-Cable Service Interface Specifications: Radio
          Frequency Interface Specification SP-RFIv2.0-I10-051209,
          Section 8.2.2.";
      }

      leaf docsIfCmtsCmStatusIpAddress {
        type inet:ipv4-address;
        config false;
        status deprecated;
        description 
         "IP address of this cable modem.  If the cable modem has no
          IP address assigned, or the IP address is unknown, this
          object returns a value of 0.0.0.0.  If the cable modem has
          multiple IP addresses, this object returns the IP address
          associated with the Cable interface.
          This object has been deprecated and replaced by
          docsIfCmtsCmStatusInetAddressType and
          docsIfCmtsCmStatusInetAddress, to enable IPv6 addressing
          in the future.";
      }

      leaf docsIfCmtsCmStatusDownChannelIfIndex {
        type if-mib:InterfaceIndexOrZero;
        config false;
        description 
         "IfIndex of the downstream channel that this CM is
          connected to.  If the downstream channel is unknown, this
          object returns a value of zero.";
      }

      leaf docsIfCmtsCmStatusUpChannelIfIndex {
        type if-mib:InterfaceIndexOrZero;
        config false;
        description 
         "For DOCSIS 2.0, indicates the ifIndex of the logical
          upstream channel (ifType 205) this CM is connected to.
          For DOCSIS 1.x, indicates the ifIndex of the upstream
           channel (ifType 129) this CM is connected to.
           If the upstream channel is unknown, this object
           returns a value of zero.";
      }

      leaf docsIfCmtsCmStatusRxPower {
        type docs-if:TenthdBmV;
        units "ThenthdBmV";
        config false;
        description 
         "The receive power as perceived for upstream data from
          this cable modem.
          If the receive power is unknown, this object returns
          a value of zero.";
        reference   
         "Data-Over-Cable Service Interface Specifications: Radio
          Frequency Interface Specification SP-RFIv2.0-I10-051209,
          Section 6.2.18.";
      }

      leaf docsIfCmtsCmStatusTimingOffset {
        type uint32 {
          range "0..4294967295";
        }
        config false;
        description 
         "A measure of the current round trip time for this CM.
          Used for timing of CM upstream transmissions to ensure
          synchronized arrivals at the CMTS.  Units are in terms
          of (6.25 microseconds/64).  Returns zero if the value
          is unknown.
          For channels requiring finer resolution, please refer to
          object docsIfCmtsCmStatusHighResolutionTimingOffset.";
        reference   
         "Data-Over-Cable Service Interface Specifications: Radio
          Frequency Interface Specification SP-RFIv2.0-I10-051209,
          Section 6.2.17.";
      }

      leaf docsIfCmtsCmStatusEqualizationData {
        type docs-if:DocsEqualizerData;
        config false;
        description 
         "Equalization data for this CM, as measured by the CMTS.
          Returns the zero-length OCTET STRING if the value is
          unknown or if there is no equalization data available
          or defined.";
        reference   
         "Data-Over-Cable Service Interface Specifications: Radio
          Frequency Interface Specification SP-RFIv2.0-I10-051209,
          Figure 8-23.";
      }

      leaf docsIfCmtsCmStatusValue {
        type enumeration {
          enum other                     { value 1; }
          enum ranging                   { value 2; }
          enum rangingAborted            { value 3; }
          enum rangingComplete           { value 4; }
          enum ipComplete                { value 5; }
          enum registrationComplete      { value 6; }
          enum accessDenied              { value 7; }
          enum operational               { value 8; }
          enum registeredBPIInitializing { value 9; }
        }
        config false;
        description 
         "Current cable modem connectivity state, as specified
          in the RF Interface Specification.  Returned status
          information is the CM status, as assumed by the CMTS,
          and indicates the following events:
          other(1)
             Any state other than below.
          ranging(2)
             The CMTS has received an Initial Ranging Request
             message from the CM, and the ranging process is not
             yet complete.
          rangingAborted(3)
             The CMTS has sent a Ranging Abort message to the CM.
          
          
          rangingComplete(4)
             The CMTS has sent a Ranging Complete message to the CM.
          ipComplete(5)
             The CMTS has received a DHCP reply message and
             forwarded it to the CM.
          registrationComplete(6)
             The CMTS has sent a Registration Response message to
             the CM.
          accessDenied(7)
             The CMTS has sent a Registration Aborted message
             to the CM.
          operational(8)
             Value 8 is considered reserved and should not be defined
             in future revisions of this MIB module to avoid conflict
             with documented implementations that support value 8 to
             indicate operational state after completing the BPI
             initialization process.
          registeredBPIInitializing(9)
             Baseline Privacy (BPI) is enabled and the CMTS is in the
             process of completing BPI initialization.  This state
             MAY last for a significant length of time if failures
             occur during the initialization process.  After
             completion of BPI initialization, the CMTS will report
             registrationComplete(6).
          The CMTS only needs to report states it is able to
          detect.";
        reference   
         "Data-Over-Cable Service Interface Specifications: Radio
          Frequency Interface Specification SP-RFIv2.0-I10-051209,
          Section 11.2.";
      }

      leaf docsIfCmtsCmStatusUnerroreds {
        type yang:counter32;
        units "codewords";
        config false;
        description 
         "Codewords received without error from this cable modem.
          Discontinuities in the value of this counter can occur
          at reinitialization of the managed system, and at other
          times as indicated by the value of
          ifCounterDiscontinuityTime for the associated ifIndex.";
        reference   
         "Data-Over-Cable Service Interface Specifications: Radio
          Frequency Interface Specification SP-RFIv2.0-I10-051209,
          Section 6.2.4.";
      }

      leaf docsIfCmtsCmStatusCorrecteds {
        type yang:counter32;
        units "codewords";
        config false;
        description 
         "Codewords received with correctable errors from this
          cable modem.
          Discontinuities in the value of this counter can occur
          at reinitialization of the managed system, and at other
          times as indicated by the value of
          ifCounterDiscontinuityTime for the associated ifIndex.";
        reference   
         "Data-Over-Cable Service Interface Specifications: Radio
          Frequency Interface Specification SP-RFIv2.0-I10-051209,
          Section 6.2.4.";
      }

      leaf docsIfCmtsCmStatusUncorrectables {
        type yang:counter32;
        units "codewords";
        config false;
        description 
         "Codewords received with uncorrectable errors from this
          cable modem.
          Discontinuities in the value of this counter can occur
          at reinitialization of the managed system, and at other
          times as indicated by the value of
          ifCounterDiscontinuityTime for the associated ifIndex.";
        reference   
         "Data-Over-Cable Service Interface Specifications: Radio
          Frequency Interface Specification SP-RFIv2.0-I10-051209,
          Section 6.2.4.";
      }

      leaf docsIfCmtsCmStatusSignalNoise {
        type docs-if:TenthdB;
        units "TenthdB";
        config false;
        description 
         "Signal/Noise ratio as perceived for upstream data from
          this cable modem.
          If the Signal/Noise is unknown, this object returns
          a value of zero.";
        reference   
         "Data-Over-Cable Service Interface Specifications: Radio
          
          
          Frequency Interface Specification SP-RFIv2.0-I10-051209,
          Tables 4-1 and 4-2.";
      }

      leaf docsIfCmtsCmStatusMicroreflections {
        type int32 {
          range "0..255";
        }
        units "-dBc";
        config false;
        description 
         "Total microreflections, including in-channel response
          as perceived on this interface, measured in dBc below
          the signal level.
          This object is not assumed to return an absolutely
          accurate value, but it gives a rough indication
          of microreflections received on this interface.
          It is up to the implementer to provide information
          as accurately as possible.
          Discontinuities in the value of this counter can occur
          at reinitialization of the managed system, and at other
          times as indicated by the value of
          ifCounterDiscontinuityTime for the associated ifIndex.";
        reference   
         "Data-Over-Cable Service Interface Specifications: Radio
          Frequency Interface Specification SP-RFIv2.0-I10-051209,
          Tables 4-1 and 4-2";
      }

      leaf docsIfCmtsCmStatusExtUnerroreds {
        type yang:counter64;
        units "codewords";
        config false;
        description 
         "Codewords received without error from this cable modem.
          Discontinuities in the value of this counter can occur
          at reinitialization of the managed system, and at other
          times as indicated by the value of
          ifCounterDiscontinuityTime for the associated ifIndex.";
        reference   
         "Data-Over-Cable Service Interface Specifications: Radio
          Frequency Interface Specification SP-RFIv2.0-I10-051209,
          Section 6.2.5.";
      }

      leaf docsIfCmtsCmStatusExtCorrecteds {
        type yang:counter64;
        units "codewords";
        config false;
        description 
         "Codewords received with correctable errors from this
          cable modem.
          Discontinuities in the value of this counter can occur
          at reinitialization of the managed system, and at other
          times as indicated by the value of
          ifCounterDiscontinuityTime for the associated ifIndex.";
        reference   
         "Data-Over-Cable Service Interface Specifications: Radio
          Frequency Interface Specification SP-RFIv2.0-I10-051209,
          Section 6.2.5.";
      }

      leaf docsIfCmtsCmStatusExtUncorrectables {
        type yang:counter64;
        units "codewords";
        config false;
        description 
         "Codewords received with uncorrectable errors from this
          cable modem.
          Discontinuities in the value of this counter can occur
          at reinitialization of the managed system, and at other
          times as indicated by the value of
          ifCounterDiscontinuityTime for the associated ifIndex.";
        reference   
         "Data-Over-Cable Service Interface Specifications: Radio
          Frequency Interface Specification SP-RFIv2.0-I10-051209,
          Section 6.2.5.";
      }

      leaf docsIfCmtsCmStatusDocsisRegMode {
        type docs-if:DocsisQosVersion;
        config false;
        description 
         "Indication of whether the CM has registered using 1.0
          Class of Service or 1.1 Quality of Service.";
        reference   
         "Data-Over-Cable Service Interface Specifications: Radio
          Frequency Interface Specification SP-RFIv2.0-I10-051209,
          Annex G.";
      }

      leaf docsIfCmtsCmStatusModulationType {
        type docs-if:DocsisUpstreamType;
        config false;
        description 
         "Indicates modulation type currently used by the CM.  Since
          this object specifically identifies PHY mode, the shared
          type is not permitted.  If the upstream channel is
          unknown, this object returns a value of zero.";
        reference   
         "Data-Over-Cable Service Interface Specifications: Radio
          Frequency Interface Specification SP-RFIv2.0-I10-051209,
          Table 8-19.";
      }

      leaf docsIfCmtsCmStatusInetAddressType {
        type inet-address:InetAddressType;
        config false;
        description 
         "The type of internet address of
          docsIfCmtsCmStatusInetAddress.  If the cable modem
          internet address is unassigned or unknown, then the
          value of this object is unknown(0).";
      }

      leaf docsIfCmtsCmStatusInetAddress {
        type inet-address:InetAddress;
        config false;
        description 
         "Internet address of this cable modem.  If the Cable
          Modem has no Internet address assigned, or the Internet
          address is unknown, the value of this object is the
          zero-length OCTET STRING.  If the cable modem has
          multiple Internet addresses, this object returns the
          Internet address associated with the Cable
          (i.e., RF MAC) interface.";
      }

      leaf docsIfCmtsCmStatusValueLastUpdate {
        type yang:timestamp;
        config false;
        description 
         "The value of sysUpTime when docsIfCmtsCmStatusValue
          was last updated.";
      }

      leaf docsIfCmtsCmStatusHighResolutionTimingOffset {
        type uint32 {
          range "0..4294967295";
        }
        config false;
        description 
         "A measure of the current round trip time for this CM.
          Used for timing of CM upstream transmissions to ensure
          synchronized arrivals at the CMTS.  Units are in terms
          of (6.25 microseconds/(64*256)).  Returns zero if the value
          is unknown.
          This is the high resolution version of object
          docsIfCmtsCmStatusTimingOffset, for channels requiring
          finer resolution.";
        reference   
         "Data-Over-Cable Service Interface Specifications: Radio
          Frequency Interface Specification SP-RFIv2.0-I10-051209,
          Section 6.2.17.";
      }
    }


    /* XXX table comments here XXX */

    list docsIfCmtsServiceEntry {

      key "ifIndex docsIfCmtsServiceId";
      description   
       "Describes the attributes of a single upstream bandwidth
        service queue.
        Entries in this table exist for each ifEntry with an
        ifType of docsCableMaclayer(127), and for each service
        queue (Service ID) within this MAC layer.
        Entries in this table are created with the creation of
        individual Service IDs by the MAC layer and removed
        when a Service ID is removed.";

      leaf ifIndex {
        type int32;
        config false;
        description 
         "Automagically generated keyref leaf.";
      }

      leaf docsIfCmtsServiceId {
        type int32 {
          range "1..16383";
        }
        config false;
        description 
         "Identifies a service queue for upstream bandwidth.  The
          attributes of this service queue are shared between the
          Cable Modem and the Cable Modem Termination System.
          The CMTS allocates upstream bandwidth to this service
          queue based on requests from the CM and on the class of
          service associated with this queue.";
      }

      leaf docsIfCmtsServiceCmStatusIndex {
        type int32 {
          range "0..65535";
        }
        config false;
        status deprecated;
        description 
         "Pointer to an entry in docsIfCmtsCmStatusTable identifying
          the cable modem using this Service Queue.  If multiple
          cable modems are using this Service Queue, the value of
          this object is zero.
          This object has been deprecated and replaced by
          docsIfCmtsServiceNewCmStatusIndex, to fix a mismatch
          of the value range with respect to docsIfCmtsCmStatusIndex
          (1..2147483647).";
      }

      leaf docsIfCmtsServiceAdminStatus {
        type enumeration {
          enum enabled   { value 1; }
          enum disabled  { value 2; }
          enum destroyed { value 3; }
        }
        config true;
        description 
         "Allows a service class for a particular modem to be
          suppressed, (re-)enabled, or deleted altogether.";
      }

      leaf docsIfCmtsServiceQosProfile {
        type int32 {
          range "0..16383";
        }
        config false;
        description 
         "The index in docsIfQosProfileTable describing the quality
          of service attributes associated with this particular
          service.  If no associated docsIfQosProfileTable entry
          exists, this object returns a value of zero.";
      }

      leaf docsIfCmtsServiceCreateTime {
        type yang:timestamp;
        config false;
        description 
         "The value of sysUpTime when this entry was created.";
      }

      leaf docsIfCmtsServiceInOctets {
        type yang:counter32;
        units "Bytes";
        config false;
        description 
         "The cumulative number of Packet Data octets received
          on this Service ID.  The count does not include the
          size of the Cable MAC header.
          Discontinuities in the value of this counter can occur
          at reinitialization of the managed system, and at other
          times as indicated by the value of
          ifCounterDiscontinuityTime for the associated ifIndex.";
      }

      leaf docsIfCmtsServiceInPackets {
        type yang:counter32;
        units "packets";
        config false;
        description 
         "The cumulative number of Packet Data packets received
          on this Service ID.
          Discontinuities in the value of this counter can occur
          at reinitialization of the managed system, and at other
          times as indicated by the value of
          ifCounterDiscontinuityTime for the associated ifIndex.";
      }

      leaf docsIfCmtsServiceNewCmStatusIndex {
        type int32 {
          range "0..2147483647";
        }
        config false;
        description 
         "Pointer (via docsIfCmtsCmStatusIndex) to an entry in
          docsIfCmtsCmStatusTable identifying the cable modem
          using this Service Queue.  If multiple cable modems are
          using this Service Queue, the value of this object is
          zero.";
      }
    }


    /* XXX table comments here XXX */

    list docsIfCmtsModulationEntry {

      key "docsIfCmtsModIndex docsIfCmtsModIntervalUsageCode";
      description   
       "Describes a modulation profile for an Interval Usage Code
        for one or more upstream channels.
        Entries in this table are created by the operator.
        
        Initial default entries MAY be created at system
        initialization time, which could report a value of
        'permanent' or 'readOnly' for docsIfCmtsModStorageType.
        A CMTS MAY reject the creation of additional Interval
        Usage Codes for a modulation profile being defined at
        Initialization time.
        No individual objects have to be specified in order
        to create an entry in this table.
        
        
        Note that some objects do not have DEFVAL clauses
        but do have calculated defaults and need not be specified
        during row creation.";


      leaf docsIfCmtsModIndex {
        type int32 {
          range "1..2147483647";
        }
        config false;
        description 
         "An index into the Channel Modulation table representing
          a group of Interval Usage Codes, all associated with the
          same channel.";
      }

      leaf docsIfCmtsModIntervalUsageCode {
        type enumeration {
          enum request         { value 1; }
          enum requestData     { value 2; }
          enum initialRanging  { value 3; }
          enum periodicRanging { value 4; }
          enum shortData       { value 5; }
          enum longData        { value 6; }
          enum advPhyShortData { value 9; }
          enum advPhyLongData  { value 10; }
          enum ugs             { value 11; }
        }
        config false;
        description 
         "An index into the Channel Modulation table that, when
          grouped with other Interval Usage Codes, fully
          instantiates all modulation sets for a given upstream
          channel.";
        reference   
         "Data-Over-Cable Service Interface Specifications: Radio
          Frequency Interface Specification SP-RFIv2.0-I10-051209,
          Table 8-20.";
      }

      leaf docsIfCmtsModControl {
        type smiv2:RowStatus;
        config true;
        description 
         "Controls and reflects the status of rows in this table.
          There is no restriction on the changing of values in this
          table while their associated rows are active, with the
          exception of:
          
          1. If a modulation profile is being referenced by one
             or more upstream channels, an attempt to set the value
             of docsIfCmtsModChannelType returns an
             'inconsistentValue' error.
          
          2. If a modulation profile is being referenced by one
             or more upstream channels, an attempt to set
             docsIfCmtsModControl to destroy(6) or notInService(2)
             returns an 'inconsistentValue' error.";
      }

      leaf docsIfCmtsModType {
        type enumeration {
          enum other  { value 1; }
          enum qpsk   { value 2; }
          enum qam16  { value 3; }
          enum qam8   { value 4; }
          enum qam32  { value 5; }
          enum qam64  { value 6; }
          enum qam128 { value 7; }
        }
        config true;
        description 
         "The modulation type used on this channel.  Returns
          other(1) if the modulation type is not
          qpsk, qam16, qam8, qam32, qam64, or qam128.
          Type qam128 is used for SCDMA channels only.
          See the reference for the modulation profiles
          implied by different modulation types.";
        reference   
         "Data-Over-Cable Service Interface Specifications: Radio
          Frequency Interface Specification SP-RFIv2.0-I10-051209,
          Tables 6-7, and 8-19.";
      }

      leaf docsIfCmtsModPreambleLen {
        type int32 {
          range "0..1536";
        }
        units "bits";
        config true;
        description 
         "The preamble length for this modulation profile in bits.
          Default value is the minimum needed by the implementation
          at the CMTS for the given modulation profile.";
        reference   
         "Data-Over-Cable Service Interface Specifications: Radio
          Frequency Interface Specification SP-RFIv2.0-I10-051209,
          Tables 6-7, and 8-19.";
      }

      leaf docsIfCmtsModDifferentialEncoding {
        type smiv2:TruthValue;
        config true;
        description 
         "Specifies whether or not differential encoding is used
          on this channel.";
        reference   
         "Data-Over-Cable Service Interface Specifications: Radio
          Frequency Interface Specification SP-RFIv2.0-I10-051209,
          Tables 6-7, and 8-19.";
      }

      leaf docsIfCmtsModFECErrorCorrection {
        type int32 {
          range "0..16";
        }
        units "Bytes";
        config true;
        description 
         "The number of correctable errored bytes (t) used in
          forward error correction code.  The value of 0 indicates
          that no correction is employed.  The number of check bytes
          appended will be twice this value.";
        reference   
         "Data-Over-Cable Service Interface Specifications: Radio
          Frequency Interface Specification SP-RFIv2.0-I10-051209,
          Tables 6-7, and 8-19.";
      }

      leaf docsIfCmtsModFECCodewordLength {
        type int32 {
          range "1..255";
        }
        units "Bytes";
        config true;
        description 
         "The number of data bytes (k) in the forward error
          correction codeword.
          This object is not used if docsIfCmtsModFECErrorCorrection
          is zero.";
        reference   
         "Data-Over-Cable Service Interface Specifications: Radio
          Frequency Interface Specification SP-RFIv2.0-I10-051209,
          Tables 6-7, and 8-19.";
      }

      leaf docsIfCmtsModScramblerSeed {
        type int32 {
          range "0..32767";
        }
        config true;
        description 
         "The 15-bit seed value for the scrambler polynomial.";
        reference   
         "Data-Over-Cable Service Interface Specifications: Radio
          Frequency Interface Specification SP-RFIv2.0-I10-051209,
          Table 8-19.";
      }

      leaf docsIfCmtsModMaxBurstSize {
        type int32 {
          range "0..255";
        }
        units "mini-slots";
        config true;
        description 
         "The maximum number of mini-slots that can be transmitted
          during this channel's burst time.  Returns zero if the
          burst length is bounded by the allocation MAP rather than
          by this profile.
          Default value is 0, except for shortData, where it is 8.";
        reference   
         "Data-Over-Cable Service Interface Specifications: Radio
          Frequency Interface Specification SP-RFIv2.0-I10-051209,
          Table 8-19.";
      }

      leaf docsIfCmtsModGuardTimeSize {
        type uint32;
        units "Symbol-times";
        config false;
        description 
         "The number of symbol-times that MUST follow the end of
          this channel's burst.  Default value is the minimum time
          needed by the implementation for this modulation profile.";
        reference   
         "Data-Over-Cable Service Interface Specifications: Radio
          Frequency Interface Specification SP-RFIv2.0-I10-051209,
          Tables 6-7, and 8-19.";
      }

      leaf docsIfCmtsModLastCodewordShortened {
        type smiv2:TruthValue;
        config true;
        description 
         "Indicates whether the last FEC codeword is truncated.";
        reference   
         "Data-Over-Cable Service Interface Specifications: Radio
          Frequency Interface Specification SP-RFIv2.0-I10-051209,
          Tables 6-7, and 8-19.";
      }

      leaf docsIfCmtsModScrambler {
        type smiv2:TruthValue;
        config true;
        description 
         "Indicates whether the scrambler is employed.";
        reference   
         "Data-Over-Cable Service Interface Specifications: Radio
          Frequency Interface Specification SP-RFIv2.0-I10-051209,
          Tables 6-7, and 8-19.";
      }

      leaf docsIfCmtsModByteInterleaverDepth {
        type uint32;
        config true;
        description 
         "ATDMA Byte Interleaver Depth (Ir).  This object returns 1
          for non-ATDMA profiles.";
        reference   
         "Data-Over-Cable Service Interface Specifications: Radio
          Frequency Interface Specification SP-RFIv2.0-I10-051209,
          Tables 6-7, and 8-19.";
      }

      leaf docsIfCmtsModByteInterleaverBlockSize {
        type uint32;
        config true;
        description 
         "ATDMA Byte Interleaver Block size (Br).  This object
          returns zero for non-ATDMA profiles ";
        reference   
         "Data-Over-Cable Service Interface Specifications: Radio
          Frequency Interface Specification SP-RFIv2.0-I10-051209,
          Tables 6-7, and 8-19.";
      }

      leaf docsIfCmtsModPreambleType {
        type enumeration {
          enum unknown { value 0; }
          enum qpsk0   { value 1; }
          enum qpsk1   { value 2; }
        }
        config true;
        description 
         "Preamble type for DOCSIS 2.0 bursts.  The value
          'unknown(0)' represents a row entry consisting only of
          DOCSIS 1.x bursts";
        reference   
         "Data-Over-Cable Service Interface Specifications: Radio
          Frequency Interface Specification SP-RFIv2.0-I10-051209,
          Tables 6-7, and 8-19.";
      }

      leaf docsIfCmtsModTcmErrorCorrectionOn {
        type smiv2:TruthValue;
        config true;
        description 
         "Trellis Code Modulation (TCM) On/Off.  This value returns
          false for non-S-CDMA profiles.";
        reference   
         "Data-Over-Cable Service Interface Specifications: Radio
          Frequency Interface Specification SP-RFIv2.0-I10-051209,
          Tables 6-7, and 8-19.";
      }

      leaf docsIfCmtsModScdmaInterleaverStepSize {
        type uint32 {
          range "0..32";
        }
        config true;
        description 
         " S-CDMA Interleaver step size.  This value returns zero
          for non-S-CDMA profiles.";
        reference   
         "Data-Over-Cable Service Interface Specifications: Radio
          Frequency Interface Specification SP-RFIv2.0-I10-051209,
          Tables 6-7, and 8-19.";
      }

      leaf docsIfCmtsModScdmaSpreaderEnable {
        type smiv2:TruthValue;
        config true;
        description 
         " S-CDMA spreader.  This value returns false for non-S-CDMA
          profiles.  Default value for IUC 3 and 4 is OFF; for
          all other IUCs it is ON.";
        reference   
         "Data-Over-Cable Service Interface Specifications: Radio
          Frequency Interface Specification SP-RFIv2.0-I10-051209,
          Tables 6-7, and 8-19.";
      }

      leaf docsIfCmtsModScdmaSubframeCodes {
        type uint32 {
          range "0..128";
        }
        config true;
        description 
         " S-CDMA sub-frame size.  This value returns zero
          for non-S-CDMA profiles.";
        reference   
         "Data-Over-Cable Service Interface Specifications: Radio
          Frequency Interface Specification SP-RFIv2.0-I10-051209,
          Table 6-7, and 8-19.";
      }

      leaf docsIfCmtsModChannelType {
        type docs-if:DocsisUpstreamType;
        config true;
        description 
         "Describes the modulation channel type for this modulation
          entry.
          All the active entries in a modulation profile (that is all
          active entries that share a common docsIfCmtsModIndex)
          MUST have the same value of docsIfCmtsModChannelType.";
        reference   
         "Data-Over-Cable Service Interface Specifications: Radio
          Frequency Interface Specification SP-RFIv2.0-I10-051209,
          Table 8-19.";
      }

      leaf docsIfCmtsModStorageType {
        type smiv2:StorageType;
        config false;
        description 
         "The storage type for this conceptual row.
          Entries with this object set to permanent(4)
          do not require write operations for read-write
          objects.";
      }
    }

    leaf docsIfCmtsQosProfilePermissions {
      type bits {
        bit createByManagement { position 0; }
        bit updateByManagement { position 1; }
        bit createByModems     { position 2; }
      }
      config true;
      description   
       "This object specifies permitted methods of creating
        entries in docsIfQosProfileTable.
        createByManagement(0) is set if entries can be created
        using SNMP.  updateByManagement(1) is set if updating
        entries using SNMP is permitted.  createByModems(2)
        is set if entries can be created based on information
        in REG-REQ MAC messages received from cable modems.
        Information in this object is only applicable if
        docsIfQosProfileTable is implemented as read-create.
        Otherwise, this object is implemented as read-only
        and returns createByModems(2).
        Either createByManagement(0) or updateByManagement(1)
        MUST be set when writing to this object.
        Note that BITS objects are encoded most significant bit
        first.  For example, if bit 2 is set, the value of this
        object is the octet string '20'H.";
    }


    /* XXX table comments here XXX */

    list docsIfCmtsMacToCmEntry {

      key "docsIfCmtsCmMac";
      description   
       "A row in the docsIfCmtsMacToCmTable.
        An entry in this table exists for each cable modem
        that is connected to the CMTS implementing this table.";


      leaf docsIfCmtsCmMac {
        type ieee:mac-address;
        config false;
        description 
         "The RF side MAC address for the referenced CM (e.g., the
          interface on the CM that has docsCableMacLayer(127) as
          its ifType).";
      }

      leaf docsIfCmtsCmPtr {
        type int32 {
          range "1..2147483647";
        }
        config false;
        description 
         "An row index into docsIfCmtsCmStatusTable.  When queried
          with the correct instance value (e.g., a CM's MAC address),
          returns the index in docsIfCmtsCmStatusTable that
          represents that CM.";
      }
    }

    leaf docsIfCmtsChannelUtilizationInterval {
      type int32 {
        range "0..86400";
      }
      units "seconds";
      config true;
      description   
       "The time interval in seconds over which the channel
        utilization index is calculated.  All upstream/downstream
        channels use the same
        docsIfCmtsChannelUtilizationInterval.
        
        
        Setting a value of zero disables utilization reporting.
        A channel utilization index is calculated over a fixed
        window applying to the most recent
        docsIfCmtsChannelUtilizationInterval.  It would therefore
        be prudent to use a relatively short
        docsIfCmtsChannelUtilizationInterval.
        It is a vendor decision whether to reset the timer when
        docsIfCmtsChannelUtilizationInterval is changed during a
        utilization sampling period.";
    }


    /* XXX table comments here XXX */

    list docsIfCmtsChannelUtilizationEntry {

      key "ifIndex"; 
      description   
       "Utilization statistics for a single upstream or downstream
        physical channel.  An entry exists in this table for each
        ifEntry with an ifType equal to
        docsCableDownstream (128)
        or docsCableUpstream (129).";

      leaf ifIndex {
        type int32;
        config false;
        description 
         "Automagically generated keyref leaf.";
      }

      leaf docsIfCmtsChannelUtIfType {
        type ianaiftype-mib:IANAifType;
        config false;
        description 
         "The secondary index into this table.  Indicates the IANA
          interface type associated with this physical channel.
          Only docsCableDownstream (128) and
          
          
          docsCableUpstream (129) are valid.";
      }

      leaf docsIfCmtsChannelUtId {
        type int32 {
          range "0..255";
        }
        config false;
        description 
         "The tertiary index into this table.  Indicates the CMTS
          identifier for this physical channel.";
      }

      leaf docsIfCmtsChannelUtUtilization {
        type int32 {
          range "0..100";
        }
        units "percent";
        config false;
        description 
         "The calculated and truncated utilization index for this
          physical upstream or downstream channel, accurate as of
          the most recent docsIfCmtsChannelUtilizationInterval.
          
          Upstream Channel Utilization Index:
          
          The upstream channel utilization index is expressed as a
          percentage of mini-slots utilized on the physical channel,
          regardless of burst type.  For an Initial Maintenance
          region, the mini-slots for the complete region are
          considered utilized if the CMTS received an upstream
          burst within the region from any CM on the physical
          channel.  For contention REQ and REQ/DATA regions, the
          mini-slots for a transmission opportunity within the
          region are considered utilized if the CMTS received an
          upstream burst within the opportunity from any CM on the
          physical channel.  For all other regions, utilized
          mini-slots are those in which the CMTS granted
          bandwidth to any unicast SID on the physical channel.
          
          For an upstream interface that has multiple logical
          upstream channels enabled, the utilization index is a
          weighted sum of utilization indices for the logical
          channels.  The weight for each utilization index is the
          percentage of upstream mini-slots allocated for the
          corresponding logical channel.
          Example:
          If 75% of bandwidth is allocated to the first logical
          channel and 25% to the second, and the utilization
          indices for each are 60 and 40, respectively, the
          
          
          utilization index for the upstream physical channel is
          (60 * 0.75) + (40 * 0.25) = 55.  This figure
          applies to the most recent utilization interval.
          
          Downstream Channel Utilization Index:
          
          The downstream channel utilization index is a percentage
          expressing the ratio between bytes used to transmit data
          versus the total number of bytes transmitted in the raw
          bandwidth of the MPEG channel.  As with the upstream
          utilization index, the calculated value represents
          the most recent utilization interval.
          Formula:
          Downstream utilization index =
          (100 * (data bytes / raw bytes))
          
          Definitions:
          Data bytes:    Number of bytes transmitted as data in the
                         docsIfCmtsChannelUtilizationInterval.
                         Identical to docsIfCmtsDownChannelCtrUsed
                         Bytes measured over the utilization
                         interval.
          Raw bandwidth: Total number of bytes available for
                         transmitting data, not including bytes
                         used for headers and other overhead.
          Raw bytes:     (raw bandwidth *
                         docsIfCmtsChannelUtilizationInterval).
                         Identical to docsIfCmtsDownChannelCtrTotal
                         Bytes measured over the utilization
                         interval.";
      }
    }


    /* XXX table comments here XXX */

    list docsIfCmtsDownChannelCounterEntry {

      key "ifIndex";
      description   
       "An entry provides a list of traffic counters for a single
        downstream channel.
        An entry in this table exists for each ifEntry with an
        ifType of docsCableDownstream(128).";

      leaf ifIndex {
        type int32;
        config false;
        description 
         "Automagically generated keyref leaf.";
      }

      leaf docsIfCmtsDownChnlCtrId {
        type int32 {
          range "0..255";
        }
        config false;
        description 
         "The Cable Modem Termination System identification
          of the downstream channel within this particular MAC
          interface.  If the interface is down, the object returns
          the most current value.  If the downstream channel ID is
          unknown, this object returns a value of 0.";
      }

      leaf docsIfCmtsDownChnlCtrTotalBytes {
        type yang:counter32;
        units "Bytes";
        config false;
        description 
         "At the CMTS, the total number of bytes in the Payload
          portion of MPEG Packets (i.e., not including MPEG header
          or pointer_field) transported by this downstream channel.
          This is the 32-bit version of
          docsIfCmtsDownChnlCtrExtTotalBytes, included to provide
          back compatibility with SNMPv1 managers.
          Discontinuities in the value of this counter can occur
          
          
          at reinitialization of the managed system, and at other
          times as indicated by the value of
          ifCounterDiscontinuityTime for the associated ifIndex.";
      }

      leaf docsIfCmtsDownChnlCtrUsedBytes {
        type yang:counter32;
        units "Bytes";
        config false;
        description 
         "At the CMTS, the total number of DOCSIS data bytes
          transported by this downstream channel.
          The number of data bytes is defined as the total number
          of bytes transported in DOCSIS payloads minus the number
          of stuff bytes transported in DOCSIS payloads.
          This is the 32-bit version of
          docsIfCmtsDownChnlCtrExtUsedBytes, included to provide
          back compatibility with SNMPv1 managers.
          Discontinuities in the value of this counter can occur
          at reinitialization of the managed system, and at other
          times as indicated by the value of
          ifCounterDiscontinuityTime for the associated ifIndex.";
      }

      leaf docsIfCmtsDownChnlCtrExtTotalBytes {
        type yang:counter64;
        units "Bytes";
        config false;
        description 
         "At the CMTS, the total number of bytes in the Payload
          portion of MPEG Packets (i.e., not including MPEG header
          or pointer_field) transported by this downstream
          channel.
          This is the 64-bit version of
          docsIfCmtsDownChnlCtrTotalBytes and will not be
          accessible to SNMPv1 managers.
          Discontinuities in the value of this counter can occur
          at reinitialization of the managed system, and at other
          times as indicated by the value of
          ifCounterDiscontinuityTime for the associated ifIndex.";
      }

      leaf docsIfCmtsDownChnlCtrExtUsedBytes {
        type yang:counter64;
        units "Bytes";
        config false;
        description 
         "At the CMTS, the total number of DOCSIS data bytes
          transported by this downstream channel.  The number
          of data bytes is defined as the total number of bytes
          transported in DOCSIS payloads minus the number of
          stuff bytes transported in DOCSIS payloads.
          This is the 64-bit version of
          docsIfCmtsDownChnlCtrUsedBytes and will not be accessible
          to SNMPv1 managers.
          Discontinuities in the value of this counter can occur
          at reinitialization of the managed system, and at other
          times as indicated by the value of
          ifCounterDiscontinuityTime for the associated ifIndex.";
      }
    }


    /* XXX table comments here XXX */

    list docsIfCmtsUpChannelCounterEntry {

      key "ifIndex";
      description   
       "List of traffic statistics for a single upstream channel.
        For DOCSIS 2.0 CMTSs, an entry in this table
        exists for each ifEntry with an ifType of
        docsCableUpstreamChannel (205).
        
        
        For DOCSIS 1.x CMTSs, an entry in this table
        exists for each ifEntry with an ifType of
        docsCableUpstream (129).";

      leaf ifIndex {
        type int32;
        config false;
        description 
         "Automagically generated keyref leaf.";
      }

      leaf docsIfCmtsUpChnlCtrId {
        type int32 {
          range "0..255";
        }
        config false;
        description 
         "The CMTS identification of the upstream channel.";
      }

      leaf docsIfCmtsUpChnlCtrTotalMslots {
        type yang:counter32;
        units "mini-slots";
        config false;
        description 
         "Current count, from CMTS initialization, of all mini-slots
          defined for this upstream logical channel.  This count
          includes all IUCs and SIDs, even those allocated to the
          NULL SID for a 2.0 logical channel that is inactive.  This
          is the 32-bit version of docsIfCmtsUpChnlCtrExtTotalMslots
          and is included for back compatibility with SNMPv1
          managers.  Support for this object is mandatory.
          Discontinuities in the value of this counter can occur
          at reinitialization of the managed system, and at other
          times as indicated by the value of
          ifCounterDiscontinuityTime for the associated ifIndex.";
      }

      leaf docsIfCmtsUpChnlCtrUcastGrantedMslots {
        type yang:counter32;
        units "mini-slots";
        config false;
        description 
         "Current count, from CMTS initialization, of unicast
          granted mini-slots on the upstream logical channel,
          regardless of burst type.  Unicast granted mini-slots are
          those in which the CMTS assigned bandwidth to any unicast
          SID on the logical channel.  However, this object does not
          include minis-lots for reserved IUCs, or grants to SIDs
          designated as meaning 'no CM'.  This is the 32-bit version
          of docsIfCmtsUpChnlCtrExtUcastGrantedMslots, and is
          included for back compatibility with SNMPv1 managers.
          Support for this object is mandatory.
          Discontinuities in the value of this counter can occur
          at reinitialization of the managed system, and at other
          times as indicated by the value of
          ifCounterDiscontinuityTime for the associated ifIndex.";
      }

      leaf docsIfCmtsUpChnlCtrTotalCntnMslots {
        type yang:counter32;
        units "mini-slots";
        config false;
        description 
         "Current count, from CMTS initialization, of contention
          mini-slots defined for this upstream logical channel.  This
          count includes all mini-slots assigned to a broadcast or
          
          
          multicast SID on the logical channel.  This is the 32-bit
          version of docsIfCmtsUpChnlCtrExtTotalCntnMslots, and is
          included for back compatibility with SNMPv1 managers.
          Support for this object is mandatory.
          Discontinuities in the value of this counter can occur
          at reinitialization of the managed system, and at other
          times as indicated by the value of
          ifCounterDiscontinuityTime for the associated ifIndex.";
      }

      leaf docsIfCmtsUpChnlCtrUsedCntnMslots {
        type yang:counter32;
        units "mini-slots";
        config false;
        description 
         "Current count, from CMTS initialization, of contention
          mini-slots utilized on the upstream logical channel.  For
          contention regions, utilized mini-slots are those in which
          the CMTS correctly received an upstream burst from any CM
          on the upstream logical channel.  This is the 32-bit
          version of docsIfCmtsUpChnlCtrExtUsedCntnMslots and is
          included for back compatibility with SNMPv1 managers.
          Support for this object is mandatory.
          Discontinuities in the value of this counter can occur
          at reinitialization of the managed system, and at other
          times as indicated by the value of
          ifCounterDiscontinuityTime for the associated ifIndex.";
      }

      leaf docsIfCmtsUpChnlCtrExtTotalMslots {
        type yang:counter64;
        units "mini-slots";
        config false;
        description 
         "Current count, from CMTS initialization, of all mini-slots
          defined for this upstream logical channel.  This count
          includes all IUCs and SIDs, even those allocated to the
          NULL SID for a 2.0 logical channel that is inactive.  This
          is the 64-bit version of docsIfCmtsUpChnlCtrTotalMslots
          and will not be accessible to SNMPv1 managers.
          Support for this object is mandatory.
          Discontinuities in the value of this counter can occur
          at reinitialization of the managed system, and at other
          times as indicated by the value of
          ifCounterDiscontinuityTime for the associated ifIndex.";
      }

      leaf docsIfCmtsUpChnlCtrExtUcastGrantedMslots {
        type yang:counter64;
        units "mini-slots";
        config false;
        description 
         "Current count, from CMTS initialization, of unicast
          granted mini-slots on the upstream logical channel,
          regardless of burst type.  Unicast granted mini-slots are
          those in which the CMTS assigned bandwidth to any unicast
          SID on the logical channel.  However, this object does not
          include mini-slots for reserved IUCs, or grants to SIDs
          designated as meaning 'no CM'.  This is the 64-bit version
          of docsIfCmtsUpChnlCtrUcastGrantedMslots and will not be
          accessible to SNMPv1 managers.
          Support for this object is mandatory.
          Discontinuities in the value of this counter can occur
          at reinitialization of the managed system, and at other
          times as indicated by the value of
          ifCounterDiscontinuityTime for the associated ifIndex.";
      }

      leaf docsIfCmtsUpChnlCtrExtTotalCntnMslots {
        type yang:counter64;
        units "mini-slots";
        config false;
        description 
         "Current count, from CMTS initialization, of contention
          mini-slots defined for this upstream logical channel.  This
          count includes all mini-slots assigned to a broadcast or
          multicast SID on the logical channel.  This is the 64-bit
          version of docsIfCmtsUpChnlCtrTotalCntnMslots and will
          not be accessible to SNMPv1 managers.
          Support for this object is mandatory.
          Discontinuities in the value of this counter can occur
          at reinitialization of the managed system, and at other
          times as indicated by the value of
          ifCounterDiscontinuityTime for the associated ifIndex.";
      }

      leaf docsIfCmtsUpChnlCtrExtUsedCntnMslots {
        type yang:counter64;
        units "mini-slots";
        config false;
        description 
         "Current count, from CMTS initialization, of contention
          
          
          mini-slots utilized on the upstream logical channel.  For
          contention regions, utilized mini-slots are those in which
          the CMTS correctly received an upstream burst from any CM
          on the upstream logical channel.  This is the 64-bit
          version of docsIfCmtsUpChnlCtrUsedCntnMslots and will not
          be accessible to SNMPv1 managers.
          Support for this object is mandatory.
          Discontinuities in the value of this counter can occur
          at reinitialization of the managed system, and at other
          times as indicated by the value of
          ifCounterDiscontinuityTime for the associated ifIndex.";
      }

      leaf docsIfCmtsUpChnlCtrCollCntnMslots {
        type yang:counter32;
        units "mini-slots";
        config false;
        description 
         "Current count, from CMTS initialization, of contention
          mini-slots subjected to collisions on the upstream logical
          channel.  For contention regions, these are the mini-slots
          applicable to bursts that the CMTS detected but could not
          correctly receive.  This is the 32-bit version of
          docsIfCmtsUpChnlCtrExtCollCntnMslots and is included for
          back compatibility with SNMPv1 managers.
          Discontinuities in the value of this counter can occur
          at reinitialization of the managed system, and at other
          times as indicated by the value of
          ifCounterDiscontinuityTime for the associated ifIndex.";
      }

      leaf docsIfCmtsUpChnlCtrTotalCntnReqMslots {
        type yang:counter32;
        units "mini-slots";
        config false;
        description 
         "Current count, from CMTS initialization, of contention
          request mini-slots defined for this upstream logical
          channel.  This count includes all mini-slots for IUC1
          assigned to a broadcast or multicast SID on the logical
          channel.  This is the 32-bit version of
          docsIfCmtsUpChnlCtrExtTotalCntnReqMslots and is included
          for back compatibility with SNMPv1 managers.
          Discontinuities in the value of this counter can occur
          at reinitialization of the managed system, and at other
          times as indicated by the value of
          
          
          ifCounterDiscontinuityTime for the associated ifIndex.";
      }

      leaf docsIfCmtsUpChnlCtrUsedCntnReqMslots {
        type yang:counter32;
        units "mini-slots";
        config false;
        description 
         "Current count, from CMTS initialization, of contention
          request mini-slots utilized on this upstream logical
          channel.  This count includes all contention mini-slots for
          IUC1 applicable to bursts that the CMTS correctly
          received.  This is the 32-bit version of
          docsIfCmtsUpChnlCtrExtUsedCntnReqMslots and is included
          for back compatibility with SNMPv1 managers.
          Discontinuities in the value of this counter can occur
          at reinitialization of the managed system, and at other
          times as indicated by the value of
          ifCounterDiscontinuityTime for the associated ifIndex.";
      }

      leaf docsIfCmtsUpChnlCtrCollCntnReqMslots {
        type yang:counter32;
        units "mini-slots";
        config false;
        description 
         "Current count, from CMTS initialization, of contention
          request mini-slots subjected to collisions on this upstream
          logical channel.  This includes all contention mini-slots
          for IUC1 applicable to bursts that the CMTS detected but
          could not correctly receive.  This is the 32-bit version of
          docsIfCmtsUpChnlCtrExtCollCntnReqMslots and is included
          for back compatibility with SNMPv1 managers.
          Discontinuities in the value of this counter can occur
          at reinitialization of the managed system, and at other
          times as indicated by the value of
          ifCounterDiscontinuityTime for the associated ifIndex.";
      }

      leaf docsIfCmtsUpChnlCtrTotalCntnReqDataMslots {
        type yang:counter32;
        units "mini-slots";
        config false;
        description 
         "Current count, from CMTS initialization, of contention
          
          
          request data mini-slots defined for this upstream logical
          channel.  This count includes all mini-slots for IUC2
          assigned to a broadcast or multicast SID on the logical
          channel.  This is the 32-bit version of
          docsIfCmtsUpChnlCtrExtTotalCntnReqDataMslots and is
          included for back compatibility with SNMPv1 managers.
          Discontinuities in the value of this counter can occur
          at reinitialization of the managed system, and at other
          times as indicated by the value of
          ifCounterDiscontinuityTime for the associated ifIndex.";
      }

      leaf docsIfCmtsUpChnlCtrUsedCntnReqDataMslots {
        type yang:counter32;
        units "mini-slots";
        config false;
        description 
         "Current count, from CMTS initialization, of contention
          request data mini-slots utilized on this upstream logical
          channel.  This includes all contention mini-slots for IUC2
          applicable to bursts that the CMTS correctly received.
          This is the 32-bit version of
          docsIfCmtsUpChnlCtrExtUsedCntnReqDataMslots and is
          included for back compatibility with SNMPv1 managers.
          Discontinuities in the value of this counter can occur
          at reinitialization of the managed system, and at other
          times as indicated by the value of
          ifCounterDiscontinuityTime for the associated ifIndex.";
      }

      leaf docsIfCmtsUpChnlCtrCollCntnReqDataMslots {
        type yang:counter32;
        units "mini-slots";
        config false;
        description 
         "Current count, from CMTS initialization, of contention
          request data mini-slots subjected to collisions on this
          upstream logical channel.  This includes all contention
          mini-slots for IUC2 applicable to bursts that the CMTS
          detected, but could not correctly receive.  This is the
          32-bit version of
          docsIfCmtsUpChnlCtrExtCollCntnReqDataMslots and is
          included for back compatibility with SNMPv1 managers.
          Discontinuities in the value of this counter can occur
          at reinitialization of the managed system, and at other
          times as indicated by the value of
          
          
          ifCounterDiscontinuityTime for the associated ifIndex.";
      }

      leaf docsIfCmtsUpChnlCtrTotalCntnInitMaintMslots {
        type yang:counter32;
        units "mini-slots";
        config false;
        description 
         "Current count, from CMTS initialization, of contention
          initial maintenance mini-slots defined for this upstream
          logical channel.  This includes all mini-slots for IUC3
          assigned to a broadcast or multicast SID on the logical
          channel.  This is the 32-bit version of
          docsIfCmtsUpChnlCtrExtTotalCntnInitMaintMslots
          and is included for back compatibility with SNMPv1
          managers.
          Discontinuities in the value of this counter can occur
          at reinitialization of the managed system, and at other
          times as indicated by the value of
          ifCounterDiscontinuityTime for the associated ifIndex.";
      }

      leaf docsIfCmtsUpChnlCtrUsedCntnInitMaintMslots {
        type yang:counter32;
        config false;
        description 
         "Current count, from CMTS initialization, of contention
          initial maintenance mini-slots utilized on this upstream
          logical channel.  This includes all contention mini-slots
          for IUC3 applicable to bursts that the CMTS correctly
          received.  This is the 32-bit version of
          docsIfCmtsUpChnlCtrExtUsedCntnInitMaintMslots
          and is included for back compatibility with SNMPv1
          managers.
          Discontinuities in the value of this counter can occur
          at reinitialization of the managed system, and at other
          times as indicated by the value of
          ifCounterDiscontinuityTime for the associated ifIndex.";
      }

      leaf docsIfCmtsUpChnlCtrCollCntnInitMaintMslots {
        type yang:counter32;
        units "mini-slots";
        config false;
        description 
         "Current count, from CMTS initialization, of contention
          initial maintenance mini-slots subjected to collisions on
          this upstream logical channel.  This includes all
          contention mini-slots for IUC3 applicable to bursts that
          the CMTS detected, but could not correctly receive.
          This is the 32-bit version of
          docsIfCmtsUpChnlCtrExtCollCntnInitMaintMslots
          and is included for back compatibility with SNMPv1
          managers.
          Discontinuities in the value of this counter can occur
          at reinitialization of the managed system, and at other
          times as indicated by the value of
          ifCounterDiscontinuityTime for the associated ifIndex.";
      }

      leaf docsIfCmtsUpChnlCtrExtCollCntnMslots {
        type yang:counter64;
        units "mini-slots";
        config false;
        description 
         "Current count, from CMTS initialization, of collision
          contention mini-slots on the upstream logical channel.
          For contention regions, these are the mini-slots applicable
          to bursts that the CMTS detected, but could not correctly
          receive.  This is the 64-bit version of
          docsIfCmtsUpChnlCtrCollCntnMslots and will not be
          accessible to SNMPv1 managers.
          Discontinuities in the value of this counter can occur
          at reinitialization of the managed system, and at other
          times as indicated by the value of
          ifCounterDiscontinuityTime for the associated ifIndex.";
      }

      leaf docsIfCmtsUpChnlCtrExtTotalCntnReqMslots {
        type yang:counter64;
        units "mini-slots";
        config false;
        description 
         "Current count, from CMTS initialization, of contention
          request mini-slots defined for this upstream logical
          channel.  This count includes all mini-slots for IUC1
          assigned to a broadcast or multicast SID on the logical
          channel.  This is the 64-bit version of
          docsIfCmtsUpChnlCtrTotalCntnReqMslots and will not be
          accessible to SNMPv1 managers.
          Discontinuities in the value of this counter can occur
          
          
          at reinitialization of the managed system, and at other
          times as indicated by the value of
          ifCounterDiscontinuityTime for the associated ifIndex.";
      }

      leaf docsIfCmtsUpChnlCtrExtUsedCntnReqMslots {
        type yang:counter64;
        units "mini-slots";
        config false;
        description 
         "Current count, from CMTS initialization, of contention
          request mini-slots utilized on this upstream logical
          channel.  This count includes all contention mini-slots for
          IUC1 applicable to bursts that the CMTS correctly
          received.  This is the 64-bit version of
          docsIfCmtsUpChnlCtrUsedCntnReqMslots and will not be
          accessible to SNMPv1 managers.
          Discontinuities in the value of this counter can occur
          at reinitialization of the managed system, and at other
          times as indicated by the value of
          ifCounterDiscontinuityTime for the associated ifIndex.";
      }

      leaf docsIfCmtsUpChnlCtrExtCollCntnReqMslots {
        type yang:counter64;
        units "mini-slots";
        config false;
        description 
         "Current count, from CMTS initialization, of contention
          request mini-slots subjected to collisions on this upstream
          logical channel.  This includes all contention mini-slots
          for IUC1 applicable to bursts that the CMTS detected,
          but could not correctly receive.  This is the 64-bit
          version of docsIfCmtsUpChnlCtrCollCntnReqMslots and will
          not be accessible to SNMPv1 managers.
          Discontinuities in the value of this counter can occur
          at reinitialization of the managed system, and at other
          times as indicated by the value of
          ifCounterDiscontinuityTime for the associated ifIndex.";
      }

      leaf docsIfCmtsUpChnlCtrExtTotalCntnReqDataMslots {
        type yang:counter64;
        units "mini-slots";
        config false;
        description 
         "Current count, from CMTS initialization, of contention
          request data mini-slots defined for this upstream logical
          channel.  This count includes all mini-slots for IUC2
          assigned to a broadcast or multicast SID on the logical
          channel.  This is the 64-bit version of
          docsIfCmtsUpChnlCtrTotalCntnReqDataMslots and will not be
          accessible to SNMPv1 managers.
          Discontinuities in the value of this counter can occur
          at reinitialization of the managed system, and at other
          times as indicated by the value of
          ifCounterDiscontinuityTime for the associated ifIndex.";
      }

      leaf docsIfCmtsUpChnlCtrExtUsedCntnReqDataMslots {
        type yang:counter64;
        units "mini-slots";
        config false;
        description 
         "Current count, from CMTS initialization, of contention
          request data mini-slots utilized on this upstream logical
          channel.  This includes all contention mini-slots for IUC2
          applicable to bursts that the CMTS correctly received.
          This is the 64-bit version of
          docsIfCmtsUpChnlCtrUsedCntnReqDataMslots and will not be
          accessible to SNMPv1 managers.
          Discontinuities in the value of this counter can occur
          at reinitialization of the managed system, and at other
          times as indicated by the value of
          ifCounterDiscontinuityTime for the associated ifIndex.";
      }

      leaf docsIfCmtsUpChnlCtrExtCollCntnReqDataMslots {
        type yang:counter64;
        units "mini-slots";
        config false;
        description 
         "Current count, from CMTS initialization, of contention
          request data mini-slots subjected to collisions on this
          upstream logical channel.  This includes all contention
          mini-slots for IUC2 applicable to bursts that the CMTS
          detected, but could not correctly receive.  This is the
          64-bit version of
          docsIfCmtsUpChnlCtrCollCntnReqDataMslots
          and will not be accessible to SNMPv1 managers.
          Discontinuities in the value of this counter can occur
          
          
          at reinitialization of the managed system, and at other
          times as indicated by the value of
          ifCounterDiscontinuityTime for the associated ifIndex.";
      }

      leaf docsIfCmtsUpChnlCtrExtTotalCntnInitMaintMslots {
        type yang:counter64;
        units "mini-slots";
        config false;
        description 
         "Current count, from CMTS initialization, of initial
          maintenance mini-slots defined for this upstream logical
          channel.  This count includes all mini-slots for IUC3
          assigned to a broadcast or multicast SID on the logical
          channel.  This is the 64-bit version of
          docsIfCmtsUpChnlCtrTotalCntnInitMaintMslots
          and will not be accessible to SNMPv1 managers.
          Discontinuities in the value of this counter can occur
          at reinitialization of the managed system, and at other
          times as indicated by the value of
          ifCounterDiscontinuityTime for the associated ifIndex.";
      }

      leaf docsIfCmtsUpChnlCtrExtUsedCntnInitMaintMslots {
        type yang:counter64;
        units "mini-slots";
        config false;
        description 
         "Current count, from CMTS initialization, of initial
          maintenance mini-slots utilized on this upstream logical
          channel.  This includes all contention mini-slots for IUC3
          applicable to bursts that the CMTS correctly received.
          This is the 64-bit version of
          docsIfCmtsUpChnlCtrUsedCntnInitMaintMslots
          and will not be accessible to SNMPv1 managers.
          Discontinuities in the value of this counter can occur
          at reinitialization of the managed system, and at other
          times as indicated by the value of
          ifCounterDiscontinuityTime for the associated ifIndex.";
      }

      leaf docsIfCmtsUpChnlCtrExtCollCntnInitMaintMslots {
        type yang:counter64;
        units "mini-slots";
        config false;
        description 
         "Current count, from CMTS initialization, of contention
          initial maintenance mini-slots subjected to collisions on
          this upstream logical channel.  This includes all
          contention mini-slots for IUC3 applicable to bursts that
          the CMTS detected, but could not correctly receive.
          This is the 64-bit version of
          docsIfCmtsUpChnlCtrCollCntnInitMaintMslots and will not
          be accessible to SNMPv1 managers.
          Discontinuities in the value of this counter can occur
          at reinitialization of the managed system, and at other
          times as indicated by the value of
          ifCounterDiscontinuityTime for the associated ifIndex.";
      }
    }
  }

} /* end of module DOCS-IF-MIB */
