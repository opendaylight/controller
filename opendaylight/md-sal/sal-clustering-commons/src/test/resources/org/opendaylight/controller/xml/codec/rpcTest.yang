/*
 * Copyright (c) 2014 Cisco Systems, Inc. and others.  All rights reserved.
 *
 * This program and the accompanying materials are made available under the
 * terms of the Eclipse Public License v1.0 which accompanies this distribution,
 * and is available at http://www.eclipse.org/legal/epl-v10.html
 */
module rpc-test {
    yang-version 1;
    namespace "urn:opendaylight:controller:rpc:test";
    prefix "rpct";

    revision 2014-07-29 {
       description "rpc test";
    }

    typedef flow-ref {
        type instance-identifier;
    }

    rpc add-flow {
        input {
            leaf id {
                type string;
            }

            leaf flow {
                type flow-ref;
            }
        }
    }
}
