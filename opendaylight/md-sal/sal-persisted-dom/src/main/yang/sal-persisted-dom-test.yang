module sal-persisted-dom-test{
    yang-version 1;
    namespace "http://netconfcentral.org/ns/persistedtest";
    prefix persistedtest;

    import config { prefix config; revision-date 2013-04-05; }
    import opendaylight-md-sal-binding { prefix mdsal; revision-date 2013-10-28; }
    import rpc-context { prefix rpcx; revision-date 2013-06-17; }
    import opendaylight-md-sal-dom {prefix sal;}
    import opendaylight-md-sal-common {prefix common;}

    organization "Netconf Central";
    contact "Sharon Aicler <saichler@cisco.com>";
    description "Persisted Database POC for MDSAL";

    revision "2014-10-20" {
          description "Persistence module initial test version";
    }

	typedef typedef-bits {
	  type bits {
	    bit first-bit {
	      description "first-bit description";
	        position 15;
	      }
	    bit second-bit; 
	  }
	}

	typedef MyType {
		type string;
	}

	typedef my-enum-type {
	    type enumeration {
	        enum TestEnum1 {
	            value 1;
	        }
	        enum TestEnum2 {
	            value 2;
	        }
	        enum TestEnum3 {
	        	value 3;
	        }    		
	    }
	}

    container sal-persisted-dom-test {
        presence "test persisted dom";
        description "Test the MDSAL model serialization and de serialization";        
        leaf MainString {
            type string;
            config false;
            mandatory true;
            description "Test simple string";
        }
        container sal-persisted-sub-container {
        	leaf SubContainerMainString {
        		type string;
        	}
        }
        list NoKeysubList {
        	leaf name {
        		type string;
        	}
	        leaf typedeftest {
	        	type MyType;
	        }
	        
	        leaf enumtest {
	        	type my-enum-type;
	        }
	        
	        leaf testInt8 {
	        	type int8;
	        }
	        
	        leaf testInt16 {
	        	type int16;
	        }
	        
	        leaf testInt32 {
	        	type int32;
	        }
	        
	        leaf testInt64 {
	        	type int64;
	        }
	        
	        leaf testDecimal64 {
	        	type decimal64{
	        		fraction-digits 4;
	        	}
	        }
	        
			leaf bitsTest {
				type typedef-bits;
			}        
	        
	        leaf testBinary {
	        	type binary;
	        }                	
        }
        list ListWithKey {
        	key id;
        	leaf id {
        		type string;
        	}
        	leaf name {
        		type string;
        	}
        }        
        leaf typedeftest {
        	type MyType;
        }
        
        leaf enumtest {
        	type my-enum-type;
        }
        
        leaf testInt8 {
        	type int8;
        }
        
        leaf testInt16 {
        	type int16;
        }
        
        leaf testInt32 {
        	type int32;
        }
        
        leaf testInt64 {
        	type int64;
        }
        
        leaf testDecimal64 {
        	type decimal64{
        		fraction-digits 4;
        	}
        }
        
		leaf bitsTest {
			type typedef-bits;
		}        
        
        leaf testBinary {
        	type binary;
        }        
    }
	augment "/sal-persisted-dom-test" {
        leaf MainString2 {
            type string;
            config false;
            mandatory true;
            description "Test simple string";
        }	
	        leaf atypedeftest {
	        	type MyType;
	        }
	        
	        leaf aenumtest {
	        	type my-enum-type;
	        }
	        
	        leaf atestInt8 {
	        	type int8;
	        }
	        
	        leaf atestInt16 {
	        	type int16;
	        }
	        
	        leaf atestInt32 {
	        	type int32;
	        }
	        
	        leaf atestInt64 {
	        	type int64;
	        }
	        
	        leaf atestDecimal64 {
	        	type decimal64{
	        		fraction-digits 4;
	        	}
	        }
	        
			leaf abitsTest {
				type typedef-bits;
			}        
	        
	        leaf atestBinary {
	        	type binary;
	        }                	        
        list AugmentSubList {
        	leaf SubAugName {
        		type string;
        	}
        }        
	}
    identity sal-persisted-dom-test {
        base config:module-type;
        config:java-name-prefix PersistedDB;
    }
}
