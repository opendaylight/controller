module referenced-module {
  namespace "referenced:module";

  prefix "refmodule";
  revision 2014-04-17 {
  }

    container cont {
        leaf lf1 {
            type instance-identifier;
        }

        leaf id-ref {
            type leafref {
                path "../../id";
            }
        }
    }

    leaf id {
        type string;
    }
}
