module leafref-module {
  namespace "leafref:module";


  prefix "lfrfmodule";

  import referenced-module { prefix refmod; revision-date 2014-04-17;}


  revision 2014-04-17 {
  }


    container cont {
        leaf lf1 {
            type instance-identifier;
        }

        leaf lf2 {
            type leafref {
                path "../lf1";
            }
        }

        leaf lf3 {
            type leafref {
                path "/refmod:cont/refmod:lf1";
            }
        }

        leaf lf4 {
            type leafref {
                path "/cont/lf1";
            }
        }

        leaf lf5 {
            type leafref {
                path "../lf1";
            }
        }

        list lst-with-lfref-key {
            key "lfref-key";

            leaf lfref-key {
                type leafref {
                    path "/refmod:cont/refmod:id-ref";
                }
            }
        }

    }
}
