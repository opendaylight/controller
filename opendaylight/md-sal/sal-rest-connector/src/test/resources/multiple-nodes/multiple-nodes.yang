module multiple-nodes {
    namespace "multiple:nodes";
    prefix "mod1";
    revision "2014-06-23";

    container cont {
        container cont1 {
            leaf lf11 {
                type string;
            }
        }

        leaf lf1 {
            type string;
        }
    }
}
