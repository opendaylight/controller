module module2 {
  namespace "module:two";  

  prefix "m2";
  revision 2014-01-17 {    
  }

    container cont_m2 {
        leaf lf1_m2 {
            type string;
        }
            uses confB_gr;
    }
        
    grouping confB_gr {
            container contB_m2 {
            }
        }
      
}
