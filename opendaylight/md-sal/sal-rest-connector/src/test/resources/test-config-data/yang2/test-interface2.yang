module test-interface2 {
    yang-version 1;
    namespace "urn:ietf:params:xml:ns:yang:test-interface2";
    prefix "snn";

    description
        "test file";   

    revision "2014-08-01" {
        description
            "Initial revision";
        reference "will be defined";
    }
    
    container class {
        list student {
            key "name";
         
            leaf name {
                type string;
            }
            leaf age {
                type string;
            }
        }
    }
}
