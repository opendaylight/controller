module module1 {
  namespace "module:one";  

  prefix "m1";
  revision 2014-01-17 {    
  }

    container cont_m1 {
        leaf lf1_m1 {
            type string;
        }
        uses confB_gr;
    }
    
    grouping confB_gr {
        container contB_m1 {
        }
    }
  
}
