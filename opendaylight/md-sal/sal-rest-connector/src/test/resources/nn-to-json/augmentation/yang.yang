module yang {
  namespace "ns:yang";  

  prefix "yng";
  revision 2013-11-26 {    
  }
  
	container cont {
		leaf lf1 {
			type string;
		}
		leaf lf2 {
            type string;
        }
		container cont1{
		    leaf lf11 {
	            type string;
	        }
		}
		
		list lst1{
		    leaf lf11 {
	            type string;
	        }
		}
		leaf-list lflst1{
		    type string;
		}
	}
}l
