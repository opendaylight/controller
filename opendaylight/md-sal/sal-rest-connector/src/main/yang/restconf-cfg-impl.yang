module restconf-cfg-impl {

    yang-version 1;
    namespace "urn:opendaylight:params:xml:ns:yang:controller:config:restconf:impl";
    prefix "restconf-impl";

    import config { prefix config; revision-date 2013-04-05; }
    import rpc-context { prefix rpcx; revision-date 2013-06-17; }
    import opendaylight-md-sal-binding { prefix mdsal; revision-date 2013-10-28; }
    import opendaylight-md-sal-dom { prefix mdsal-dom; revision-date 2013-10-28; }

    description
        "This module contains the  YANG config definitions for
        Restconf  implementation.";

    revision "2014-07-24" {
        description
            "Initial revision.";
    }

    // This is the definition of the service implementation as a module identity.
    identity restconf-service {
            base config:module-type;

            // Specifies the prefix for generated java classes.
            config:java-name-prefix RestconfImpl;
    }

    // Augments the 'configuration' choice node under modules/module.
    augment "/config:modules/config:module/config:configuration" {
        case restconf-service {
            when "/config:modules/config:module/config:type = 'restconf-service'";

            container data-broker {
                uses config:service-ref {
                    refine type {
                        mandatory false;
                        config:required-identity mdsal-dom:dom-data-broker;

                    }
                }
            }
/*           container schema-service {
                            uses config:service-ref {
                                refine type {
                                    mandatory false;
                                    config:required-identity mdsal-dom:schema-service;

                                }
                            }
                        }
            container mount-service {
                uses config:service-ref {
                    refine type {
                        mandatory false;
                        config:required-identity TODO;

                    }
                }
            } */

            container dom-registry {
                uses config:service-ref {
                    refine type {
                        mandatory true;
                        config:required-identity mdsal-dom:dom-broker-osgi-registry;
                    }
                }
            }
          }
        }

}
