module forwardingrules-manager {

    yang-version 1;
    namespace "urn:opendaylight:params:xml:ns:yang:controller:md:sal:forwardingrules-manager";
    prefix "frm";

    import config { prefix config; revision-date 2013-04-05; }
    import opendaylight-md-sal-binding { prefix mdsal; revision-date 2013-10-28; }

    description
        "This module contains the base YANG definitions for
        forwardingrules-manager implementation.";

    revision "2014-09-25" {
        description
            "Initial revision.";
    }

    identity forwardingrules-manager {
            base config:module-type;
            config:java-name-prefix ForwardingRulesManager;
    }

    augment "/config:modules/config:module/config:configuration" {
        case forwardingrules-manager {
            when "/config:modules/config:module/config:type = 'forwardingrules-manager'";

            container rpc-registry {
                uses config:service-ref {
                    refine type {
                        mandatory true;
                        config:required-identity mdsal:binding-rpc-registry;
                    }
                }
            }

            container notification-service {
                uses config:service-ref {
                    refine type {
                        mandatory true;
                        config:required-identity mdsal:binding-notification-service;
                    }
                }
            }

            container data-broker {
                uses config:service-ref {
                    refine type {
                        mandatory false;
                        config:required-identity mdsal:binding-async-data-broker;
                    }
                }
            }

            container frm-settings {
                leaf clean-alien-flows-on-reconciliation {
                    type boolean;
                }
            }
        }
    }

}
