module clustering-service-provider {

    yang-version 1;
    namespace "urn:opendaylight:params:xml:ns:yang:controller:config:clustering-service-provider";
    prefix "clustering-service-provider";

    import config { prefix config; revision-date 2013-04-05; }
    import opendaylight-md-sal-binding { prefix mdsal; revision-date 2013-10-28; }
    import clustering-api { prefix clustering-api; revision-date 2015-04-07; }

    description
        "This module contains the base YANG definitions for the clustering service provider implementation.
         Copyright (c)2015 Cisco Systems, Inc. All rights reserved.

         This program and the accompanying materials are made available
         under the terms of the Eclipse Public License v1.0 which
         accompanies this distribution, and is available at
         http://www.eclipse.org/legal/epl-v10.html";

    revision "2015-04-07" {
        description "Initial revision.";
    }

    identity clustering-service-provider {
        base config:module-type;
        config:provided-service clustering-api:clustering-role-service;
        // Specifies the prefix for generated java classes.
        config:java-name-prefix SalClusteringServiceProvider;
    }

    // Augments the 'configuration' choice node under modules/module.
    augment "/config:modules/config:module/config:configuration" {
        case clustering-service-provider {
            when "/config:modules/config:module/config:type = 'clustering-service-provider'";
                container notification-service {
                    uses config:service-ref {
                        refine type {
                            mandatory true;
                            config:required-identity mdsal:binding-notification-service;
                        }
                    }
                }

        }
    }
}
