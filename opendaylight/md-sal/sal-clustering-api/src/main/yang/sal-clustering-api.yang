module sal-clustering-api {

    yang-version 1;
    namespace "urn:opendaylight:params:xml:ns:yang:controller:config:sal-clustering-api";
    prefix "sal-clustering-api";

    import config { prefix config; revision-date 2013-04-05; }

    description "This module contains the base YANG definitions for the sal-clustering api ";

    revision "2015-04-07" {
        description "Initial revision.";
    }

    identity sal-clustering-role-service {
        base config:service-type;
        config:java-class "org.opendaylight.controller.md.sal.clustering.api.ClusteringRoleService";
    }

    typedef shard-role {
            type enumeration {
                enum NONE {
                    description "No role";
                }
                enum FOLLOWER {
                    description "Follower role";
                }
                enum CANDIDATE {
                    description "Candidate role";
                }
                enum LEADER {
                    description "Leader role";
                }
                enum ISOLATED-LEADER {
                    description "Isolated Leader role";
                }
            }
    }

    grouping shard-role-change {
            leaf member-id {
                type string;
            }

            leaf shard-id {
                type string;
            }

            leaf old-role {
                type shard-role;
                description "Old role of the datastore shard";
            }

            leaf new-role {
                type shard-role;
                description "New role of the datastore shard";
            }
    }

}
