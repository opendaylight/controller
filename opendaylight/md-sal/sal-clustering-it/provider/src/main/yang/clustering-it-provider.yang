module clustering-it-provider {

    yang-version 1;
    namespace "urn:opendaylight:params:xml:ns:yang:controller:config:clustering-it-provider";
    prefix "clustering-it-provider";

    import config { prefix config; revision-date 2013-04-05; }
    import opendaylight-md-sal-binding { prefix mdsal; revision-date 2013-10-28; }

    description
        "This module contains the base YANG definitions for
        clustering-it-provider implementation.";

    revision "2014-08-19" {
        description
            "Initial revision.";
    }

    // This is the definition of the service implementation as a module identity.
    identity clustering-it-provider {
            base config:module-type;

            // Specifies the prefix for generated java classes.
            config:java-name-prefix ClusteringItProvider;
    }

    // Augments the 'configuration' choice node under modules/module.
    augment "/config:modules/config:module/config:configuration" {
        case clustering-it-provider {
            when "/config:modules/config:module/config:type = 'clustering-it-provider'";

            container rpc-registry {
                uses config:service-ref {
                    refine type {
                        mandatory true;
                        config:required-identity mdsal:binding-rpc-registry;
                    }
                }
            }

            container notification-service {
                uses config:service-ref {
                    refine type {
                        mandatory true;
                        config:required-identity mdsal:binding-notification-service;
                    }
                }
            }

            container data-broker {
                uses config:service-ref {
                    refine type {
                        mandatory false;
                        config:required-identity mdsal:binding-async-data-broker;
                    }
                }
            }
        }
    }
}
