module opendaylight-md-sal-common {
	yang-version 1;
    namespace "urn:opendaylight:params:xml:ns:yang:controller:md:sal:common";
    prefix "md-sal-common";
    
    description
        "Common definition for MD-SAL.";
 
    revision "2013-10-28" {
        description
            "Initial revision";
    }
    
    grouping rpc-routing-table {
        
        leaf routing-context {
            type string;
        }
        list routes {
            leaf path {
                type string;
            }
            leaf destination {
                type string;
            }
        }
    
    }

    grouping rpc-router {
        leaf module {
            type string;
        }
        container routing-tables {
            list routing-table {
                uses rpc-routing-table;
            }
        }
    }

    grouping rpc-state {
        list rpc-router {
            uses rpc-router;
        }
    }
    
    grouping notification-state {
        container notifications {
            leaf published {
                type uint32;
            }
        }
    }
    
    grouping data-state {
        container transactions {
            leaf created {
                type uint32;
            }
            leaf submitted {
                type uint32;
            }
            leaf successful {
                type uint32;
            }
            leaf failed {
                type uint32;
            }
        }
    }
}
