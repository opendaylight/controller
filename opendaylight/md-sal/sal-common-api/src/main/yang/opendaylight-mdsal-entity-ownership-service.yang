// Contents of "opendaylight-mdsal-entity-ownership-service"
module opendaylight-mdsal-entity-ownership-service {
    yang-version 1;
    namespace "urn:opendaylight:params:xml:ns:yang:md:sal:core:spi:entity-ownership-service";
    prefix "mdsal-entity-ownership-service";

    import config { prefix config; revision-date 2013-04-05; }

    description "MD-SAL EntityOwnershipService interface definition";

    revision "2016-06-20" {
        description "Initial revision";
    }

    identity entity-ownership-service {
        base "config:service-type";
        config:java-class "org.opendaylight.mdsal.binding.api.clustering.EntityOwnershipService";
        config:disable-osgi-service-registration;
    }

    identity dom-entity-ownership-service {
        base "config:service-type";
        config:java-class  "org.opendaylight.mdsal.dom.api.clustering.DOMEntityOwnershipService";
        config:disable-osgi-service-registration;
    }
}
