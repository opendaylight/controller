module possum {

    yang-version 1;

    namespace "urn:opendaylight:params:xml:ns:yang:controller:config:sal-clustering-it:possum";

    prefix possum;

	import ietf-inet-types { prefix "inet"; revision-date 2010-09-24; }
	
    organization "Netconf Central";

    contact
      "Harman Singh <harmasin@cisco.com>";

    description
      "YANG model for possum for test application";

    revision "2015-05-13" {
      description
        "Clustering sample app";
    }
    
    typedef possum-id {
      type inet:uri;
      description "An identifier for possum entry.";
    }

    typedef possumentry-ref {
      type instance-identifier;
      description "A reference that points to an people:people/person in the data tree.";
    }

    identity possumentry-context {
        description "A person-context is a classifier for person elements which allows an RPC to provide a service on behalf of a particular element in the data tree.";
    }

    grouping possumentry {
      description "Describes the contents of a possum entry -
                       Details of the possum manufacturer, model etc";
      leaf id {
        type possum-id;
        description "identifier of single list of entries.";
      }

      leaf model {
        type string;
      }
      leaf manufacturer {
        type string;
      }

      leaf year {
        type uint32;
      }

      leaf category {
        type string;
      }
    }
    
    container possums {
      description
        "Top-level container for all possum objects.";

      list possumentry {
      	key "id";
      	description "A list of possums (as defined by the 'grouping possumentry').";
      	uses possumentry;
      }
    }

//    rpc add-possumentry {
//      description
//        "Add a possum entry into database";
//      input {
//        uses possumentry;
//      }
//    }

}
