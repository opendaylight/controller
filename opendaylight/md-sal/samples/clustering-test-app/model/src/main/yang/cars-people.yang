module cars-people {

    yang-version 1;

    namespace "urn:opendaylight:params:xml:ns:yang:controller:config:sal-clustering-it:cars-people";

    prefix cars;

	  import ietf-inet-types { prefix "inet"; revision-date 2010-09-24; }
	  import cars { prefix "c"; revision-date 2014-08-18; }
	  import people { prefix "people"; revision-date 2014-08-18; }

    organization "Netconf Central";

    contact
      "Harman Singh <harmasin@cisco.com>";

    description
      "YANG model for car for test application";

    revision "2014-08-18" {
      description
        "Clustering sample app";
    }

    container cars-people {
      description
       "Top-level container for all people cars map";

      list car-person {
        key "car-id person-id";
        description "A mapping of cars and people.";
        leaf car-id {
          type c:car-id;
        }

        leaf person-id {
          type people:person-id;
        }
      }
    }
}
