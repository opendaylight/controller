module icmpdata {

    yang-version 1;

    namespace "http://opendaylight.org/samples/icmp/data";
    prefix "icmpdata";

    import ietf-inet-types { prefix inet; }

    organization "Brocade Communication Systems";

    contact "Devin Avery <devin.avery@brocade.com>";

    description "This defines a module which we want to mount onto the end of
    every ICMP device that is discovered";

    revision "2014-05-15" {
        description "ICMP discovery - initial revision";
    }

	//Note: we are providing two ways to get the same data (i.e. to perform a ping). In a real example you will NOT want to do this.
	//You would want to have one consistent way to perform the operation. In this example, we are trying
	//to illustrate how you interact with / extend MD-SAL, while keeping the business logic simple and easy to understand.
	//This is why we have is-available as an operation attribute, and a sendPingNow RPC call. 
    container icmpdata {
        presence "Device";

        leaf is-available {
           type boolean;
           description "When read, forces an active read to the device.";
           config false;
        }

    }

    rpc sendPingNow {
        description "Sends an ICMP ping to the device.";

        output {
            leaf rtt {
                type uint32;
            }
        }
    }

}
