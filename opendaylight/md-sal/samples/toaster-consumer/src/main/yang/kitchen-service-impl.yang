// vi: set smarttab et sw=4 tabstop=4:
module kitchen-service-impl {

    yang-version 1;
    namespace "urn:opendaylight:params:xml:ns:yang:controller:config:kitchen-service:impl";
    prefix "kitchen-service-impl";

    import config { prefix config; revision-date 2013-04-05; }
    import rpc-context { prefix rpcx; revision-date 2013-06-17; }

    import opendaylight-md-sal-binding { prefix mdsal; revision-date 2013-10-28; }
    import opendaylight-sal-binding-broker-impl { prefix binding-impl; revision-date 2013-10-28; }

    description
        "This module contains the base YANG definitions for
        kitchen-service impl implementation.";

    revision "2014-01-31" {
        description
            "Initial revision.";
    }

    // This is the definition of kitchen service interface identity.
    identity kitchen-service {
        base "config:service-type";
        config:java-class "org.opendaylight.controller.sample.kitchen.api.KitchenService";
    }

    // This is the definition of kitchen service implementation module identity. 
    identity kitchen-service-impl {
            base config:module-type;
            config:provided-service kitchen-service;
            config:java-name-prefix KitchenService;
    }

    augment "/config:modules/config:module/config:configuration" {
        case kitchen-service-impl {
            when "/config:modules/config:module/config:type = 'kitchen-service-impl'";

            container rpc-registry {
                uses config:service-ref {
                    refine type {
                        mandatory true;
                        config:required-identity mdsal:binding-rpc-registry;
                    }
                }
            }

            container notification-service {
                uses config:service-ref {
                    refine type {
                        mandatory true;
                        config:required-identity binding-impl:binding-new-notification-service;
                    }
                }
            }
        }
    }
    
    augment "/config:modules/config:module/config:state" {
        case kitchen-service-impl {
            when "/config:modules/config:module/config:type = 'kitchen-service-impl'";
            
            rpcx:rpc-context-instance "make-scrambled-with-wheat-rpc";
        }
    }

    identity make-scrambled-with-wheat-rpc;

    rpc make-scrambled-with-wheat  {
        description
          "Shortcut JMX call to make breakfast with scrambled eggs and wheat toast for testing.";
          
        input {
            uses rpcx:rpc-context-ref {
                refine context-instance {
                    rpcx:rpc-context-instance make-scrambled-with-wheat-rpc;
                }
            }
        }
        
        output {
            leaf result {
                type boolean;
            }
        }
    }
}
