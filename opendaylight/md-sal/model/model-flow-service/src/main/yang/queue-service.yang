module sal-queue {
    namespace "urn:opendaylight:queue:service";
    prefix queue;

    import yang-ext {prefix ext; revision-date "2013-07-09";}
    import opendaylight-inventory {prefix inv; revision-date "2013-08-19";}
    import opendaylight-queue-types {prefix queue-type; revision-date "2013-09-25";}

    revision "2013-11-07" {
        description "Initial revision of queue service";
    }        
    
   
     
    rpc get-queue {
        output {
            uses queue-type:queue-packet;
        }
    }  
    
    grouping node-queue {
        uses "inv:node-context-ref";
     
        uses queue-type:queue-list;
    }
    notification queue-get-config-reply {
        uses node-queue;
    }
}
