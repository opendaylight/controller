module sal-table {
    namespace "urn:opendaylight:table:service";
    prefix table;

    import opendaylight-inventory {prefix inv;revision-date "2013-08-19";}
    import opendaylight-table-types {prefix table-type;revision-date "2013-10-26";}
    import flow-capable-transaction {prefix tr;}

    revision "2013-10-26" {
        description "Initial revision of table service";
    }
    
    /** Base configuration structure **/
    grouping table-update {
        uses "inv:node-context-ref";
        container original-table {
            uses table-type:table-features;
        }
        container updated-table {
            uses table-type:table-features;
        }
    }
    
    rpc update-table {
        input {
            uses table-update;
            uses tr:transaction-aware;
        }
        output {
            uses tr:transaction-aware;
        }
    }
    
    notification table-updated {
        uses "inv:node-context-ref";
        uses tr:transaction-aware;
        leaf moreReplies {
            type boolean;
        }
        uses table-type:table-features;
    }
}
