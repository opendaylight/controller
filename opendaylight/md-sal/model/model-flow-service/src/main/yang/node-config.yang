module node-config {
    namespace "urn:opendaylight:module:config";
    prefix node-config;

    import flow-capable-transaction {prefix tr;}
    import opendaylight-inventory {prefix inv;revision-date "2013-08-19";}

    revision "2014-10-15" {
        description "Initial revision of node configuration service";
    }

    grouping node-ref {
        uses "inv:node-context-ref";
    }



    /** Base configuration structure **/
    grouping node-config {
        leaf flag {
            type string;
            description "Switch config flag. Expected values FRAGNORMAL, OFPCFRAGDROP, OFPCFRAGREASM, OFPCFRAGMASK";
        }
        leaf miss-search-length{
            type uint16;
        }
    }

    rpc set-config {
        input {
            uses node-config;
            uses tr:transaction-aware;
            uses node-ref;
        }
        output {
            uses tr:transaction-aware;
        }
    }
}
