module sal-flow-config {
    namespace "urn:opendaylight:flow:config";
    prefix flow-cfg;

    import sal-flow {prefix flow;}

    revision "2013-08-19" {
        description "Initial revision of flow service";
    }


    container flows {
        list flow {
            key "id";
            
            leaf id {
                type string;
            }
            uses flow:node-flow;
            /**
                container match;
            
            **/
        }
    }
}
