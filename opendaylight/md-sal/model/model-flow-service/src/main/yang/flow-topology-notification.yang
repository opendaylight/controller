module flow-topology-discovery {
    namespace "urn:opendaylight:flow:topology:discovery";
    prefix flow-node-topo;

    import yang-ext {prefix ext; revision-date "2013-07-09";}
    import opendaylight-inventory {prefix inv;revision-date "2013-08-19";}
    
    revision "2013-08-19" {
        description "Flow Capable Node extensions to the Inventory model";
    }
    

    grouping link {
        leaf source {
            type inv:node-connector-ref;
        }
        leaf destination {
            type inv:node-connector-ref;
        }
    }


    notification link-discovered {
        uses link;
    }
    
    notification link-overutilized {
        uses link;
    }
    
    notification link-removed {
        uses link;
    }
    
    notification link-utilization-normal {
        uses link;
    }

    rpc solicit-refresh {
    
    }

}
