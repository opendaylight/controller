module sal-port {
    namespace "urn:opendaylight:port:service";
    prefix port;

    import yang-ext {prefix ext; revision-date "2013-07-09";}
    import opendaylight-inventory {prefix inv;revision-date "2013-08-19";}
    import opendaylight-port-types {prefix port-type;revision-date "2013-09-25";}
    import flow-capable-transaction {prefix tr;}

    revision "2013-11-07" {
        description "Initial revision of port service";
    }        
    
    grouping node-port {
        uses "inv:node-context-ref";
        
        uses port-type:flow-port-status;
    }

   grouping port-config {
   		 uses "inv:node-context-ref";
         
         uses port-type:port;
     }
     
   rpc update-port {
         input {
            uses port-config;
            uses tr:transaction-aware;
        }
        output {
            uses tr:transaction-aware;
        }
    }
     
    rpc get-port {
        output {
            uses port-type:flow-capable-port;
        }
    }
    
    notification port-updated {
        uses port-config;
        uses tr:transaction-aware;
    }
    
    notification port-removed {
        uses node-port;       
    }
}
