module sal-group {
    namespace "urn:opendaylight:group:service";
    prefix group;

    import yang-ext {prefix ext; revision-date "2013-07-09";}
    import opendaylight-inventory {prefix inv;revision-date "2013-08-19";}
    import ietf-inet-types {prefix inet;revision-date 2010-09-24;}
    import opendaylight-group-types {prefix group-type;revision-date 2013-10-18;}
    import flow-capable-transaction {prefix tr;}

    revision "2013-09-18" {
        description "Initial revision of group service";
    }        
    
    grouping node-group {
        uses "inv:node-context-ref";        
        uses group-type:group;
    }

    /** Base configuration structure **/
    grouping group-update {
        uses "inv:node-context-ref";
        
        container original-group {
            uses group-type:group;
        }
        container updated-group {
            uses group-type:group;
        }
    }

    rpc add-group {
        input {
            uses tr:transaction-metadata;
            leaf group-ref {
                type group-type:group-ref;
            }
            uses node-group;            
        }
        output {
            uses tr:transaction-aware;
        }
    }

    rpc remove-group {
        input {
            uses tr:transaction-metadata;
            leaf group-ref {
                type group-type:group-ref;
            }
            uses node-group;            
        }
        output {
            uses tr:transaction-aware;
        }
    }

    rpc update-group {
        input {
            uses tr:transaction-metadata;
            leaf group-ref {
                type group-type:group-ref;
            }
            uses group-update;            
        }
        output {
            uses tr:transaction-aware;
        }
    } 

    notification group-added {
        uses tr:transaction-metadata;
        leaf group-ref {
            type group-type:group-ref;
        }
        uses node-group;
        uses tr:transaction-aware;
    }

    notification group-updated {
        uses tr:transaction-metadata;
        leaf group-ref {
            type group-type:group-ref;
        }
        uses node-group;
        uses tr:transaction-aware;
    }

    notification group-removed {
        uses tr:transaction-metadata;
        leaf group-ref {
            type group-type:group-ref;
        }
        uses node-group;
        uses tr:transaction-aware;
    }    
}
