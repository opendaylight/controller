module flow-capable-transaction {
    namespace "urn:opendaylight:flow:transaction";
    prefix type;

    import opendaylight-inventory {prefix inv; revision-date "2013-08-19";}
    import ietf-inet-types {prefix inet; revision-date "2010-09-24";}
    import yang-ext {prefix ext; revision-date "2013-07-09";}
    import restconf-doc-ext { prefix "restconf-ext"; }

    revision "2013-11-03" {
        description "Initial revision";
    }

    typedef transaction-id {
        type uint64;
    }
    // This refers to MD-SAL transaction reference.
    grouping transaction-metadata {
        leaf transaction-uri {
            type inet:uri;
        }
    }

    grouping transaction-aware {
        leaf transaction-id {
            type transaction-id;
        }
    }

    grouping multipart-transaction-aware {
        uses transaction-aware;

        leaf moreReplies {
            type boolean;
            default false;
        }
    }

    rpc get-next-transaction-id {
        input {
            leaf node {
                ext:context-reference "inv:node-context";
                type inv:node-ref;
            }
        }
        output {
            uses transaction-aware;
        }
    }

    // Barier request?
    rpc finish-transaction {
        input {
            leaf node {
                ext:context-reference "inv:node-context";
                type inv:node-ref;
            }
            leaf transaction-id {
                type transaction-id;
            }
        }
    }
    
    restconf-ext:module-scope-private;

}
