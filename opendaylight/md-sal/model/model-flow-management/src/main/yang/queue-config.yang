module queue-management {
    namespace "urn:opendaylight:queue:config";
    prefix queue-cfg;

    import yang-ext {prefix ext; revision-date "2013-07-09";}
    import opendaylight-inventory {prefix inv;revision-date "2013-08-19";}      
     
    import opendaylight-queue-types {prefix queue; revision-date "2013-09-25";}

   
    revision "2013-10-24" {
        description "Initial revision of queue service";
    }

    grouping queue-entry {
        leaf node {
            type inv:node-connector-ref;
           
        }
        uses queue:get-queue-config-request;
    }   
     
    container queues {
        list queue {
            key "id node"; 
                        
            leaf id {
                type uint32;
            }                       
            
            uses queue-entry;
        }
    }    
}
