module flow-management {
    namespace "urn:opendaylight:flow:config";
    prefix flow-cfg;

    import yang-ext {prefix ext; revision-date "2013-07-09";}
    import opendaylight-inventory {prefix inv;revision-date "2013-08-19";}
    import opendaylight-flow-types {prefix flow;}

    revision "2013-08-19" {
        description "Initial revision of flow service";
    }


    grouping flow-entry {
        leaf node {
            type inv:node-ref;
        }
        uses flow:flow;
    }

    container flows {
        list flow {
            key "node id"; 

            leaf id {
                type uint32;
            }
            uses flow-entry;
        }
    }
}
