module meter-management {
    namespace "urn:opendaylight:meter:config";
    prefix meter-cfg;

    import opendaylight-inventory {prefix inv;revision-date "2013-08-19";}  
    import meter-types {prefix meter;}

    revision "2013-10-24" {
        description "Initial revision of meter service";
    }

    grouping meter-entry {
        leaf node {
            type inv:node-ref;
        }
        uses meter:meter;
    }   
     
    container meters {
        list meter {
            key "id node"; 
                        
            leaf id {
                type uint32;
            }                    
            
            uses meter-entry;
        }
    }    
}
