module group-management {
    namespace "urn:opendaylight:group:config";
    prefix group-cfg;

    import yang-ext {prefix ext; revision-date "2013-07-09";}
    import opendaylight-inventory {prefix inv;revision-date "2013-08-19";}  
    import opendaylight-group-types {prefix group;}

    revision "2013-10-24" {
        description "Initial revision of group service";
    }

    grouping group-entry {
        leaf node {
            type inv:node-ref;
        }
        uses group:group;
    }   
     
    container groups {
        list group {
            key "id node"; 
                        
            leaf id {
                type uint32;
            }                       
            
            uses group-entry;
        }
    }    
}
