module queue-management {
    namespace "urn:opendaylight:queue:config";
    prefix queue-cfg;

    import opendaylight-inventory {prefix inv;revision-date "2013-08-19";}      
     
    import opendaylight-queue-types {prefix queue-types; revision-date "2013-09-25";}

   
    revision "2013-10-24" {
        description "Initial revision of queue service";
    }


    container queues {
        list queue-entry {
            key "queue-id";
            uses queue-types:queue;
        }
    }
}
