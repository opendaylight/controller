module opendaylight-group-statistics {
    namespace "urn:opendaylight:group:statistics";
    prefix groupstat;

    import yang-ext {prefix ext; revision-date "2013-07-09";}
    import opendaylight-inventory {prefix inv;revision-date "2013-08-19";}
    import opendaylight-group-types {prefix group-types;revision-date "2013-10-18";}
    import flow-capable-transaction {prefix tr;}
    import flow-node-inventory {prefix fni;}
    import restconf-doc-ext { prefix "restconf-ext"; }

    contact
        "Anilkumar Vishnoi
        Email: avishnoi@in.ibm.com";
            
    revision "2013-11-11" {
        description "Initial revision of group statistics service";
    }
    
    grouping group-statistics {
        container group-statistics {
            //config "false";
            uses group-types:group-statistics;
        }
    }    
    
    augment "/inv:nodes/inv:node/fni:group" {
        ext:augment-identifier "node-group-statistics";
        uses group-statistics;
    }

    grouping group-desc {
        container group-desc {
            //config "false";
            uses group-types:group;
        }
    }
    
    augment "/inv:nodes/inv:node/fni:group" {
        ext:augment-identifier "node-group-desc-stats";
        uses group-desc;
    }

    grouping group-features {
            container group-features {
            //config "false";
            uses group-types:group-features-reply;
        }
    }
        
    augment "/inv:nodes/inv:node" {
        ext:augment-identifier "node-group-features";
        uses group-features;
        restconf-ext:children-scope-private;
    }

    // RPC calls
    rpc get-all-group-statistics {
        input {
            uses inv:node-context-ref;
        }
        output {
            uses group-types:group-statistics-reply;
            uses tr:transaction-aware;
        }
    
    }
    
    rpc get-group-statistics {
        input {
            uses inv:node-context-ref;
            leaf group-id{
                type group-types:group-id;
            }
           
        }
        output {
            uses group-types:group-statistics-reply;
            uses tr:transaction-aware;
        }
    
    }
    
    rpc get-group-description {
        input {
            uses inv:node-context-ref;
        }
        output {
            uses group-types:group-desc-stats-reply;
            uses tr:transaction-aware;
        }
    }
    
    rpc get-group-features {
        input {
            uses inv:node-context-ref;
        }
        output {
            uses group-types:group-features-reply;
            uses tr:transaction-aware;
        }
    }
    

    //Notification calls
    
    notification group-statistics-updated {
        uses inv:node;
        uses group-types:group-statistics-reply;
        uses tr:multipart-transaction-aware;
    }
    
    notification group-desc-stats-updated {
        uses inv:node;
        uses group-types:group-desc-stats-reply;
        uses tr:multipart-transaction-aware;
    }

    notification group-features-updated {
        uses inv:node;
        uses group-types:group-features-reply;
        uses tr:multipart-transaction-aware;
    }
}
