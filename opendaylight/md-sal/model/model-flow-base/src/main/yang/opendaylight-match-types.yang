module opendaylight-match-types {
    namespace "urn:opendaylight:model:match:types";
    prefix "match";

    import ietf-inet-types {prefix inet; revision-date "2010-09-24";}
    import ietf-yang-types {prefix yang; revision-date "2010-09-24";}
    import opendaylight-l2-types {prefix l2t;revision-date "2013-08-27";}
    import opendaylight-inventory {prefix inv;revision-date "2013-08-19";}

    revision "2013-10-26" {
        description "Initial revision of match types";
    }

    grouping "mac-address-filter" {
        leaf address {
            mandatory true;
            type yang:mac-address;
        }
        leaf mask {
            type yang:mac-address;
        }
    }

    grouping "of-metadata" {
        leaf metadata {
            type uint64;
        }

        leaf metadata-mask {
            type uint64;
        }
    }

    grouping ethernet-source-attributes{
        description "Ethernet source address.";
        uses mac-address-filter;
    }
    
    grouping ethernet-destination-attributes {
        description "Ethernet destination address.";
        uses mac-address-filter;
    }
    
    grouping ethernet-type-attributes {
        description "Ethernet frame type.";

        leaf type {
            mandatory true;
            type l2t:ether-type; // Needs to define that as general model
        }
    }
    
    // TODO - not sure what to do about vlan-id present
    grouping "vlan-match-fields" {
        container vlan-id {
            description "VLAN id.";
            presence "Match field is active and set";

            leaf vlan-id-present {
                type boolean;
            }

            leaf vlan-id {
                type l2t:vlan-id;
            }
        }
        leaf vlan-pcp {
            description "VLAN priority.";
            type l2t:vlan-pcp;
        }
    }

    grouping ip-protocol-attributes {
        leaf ip-protocol {
            description "IP protocol.";
            type uint8;
        }   
    }
    
    grouping ip-dscp-attributes {
        leaf ip-dscp {
            description "IP DSCP (6 bits in ToS field).";
            type inet:dscp;
        }
    }
    
    grouping ip-ecn-attributes {
        leaf ip-ecn {
            description "IP ECN (2 bits in ToS field).";
            type uint8;
        }
    }
    
    grouping ip-version-attributes {
        leaf ip-version {
            description "IP Proto (IPv4 or IPv6 Protocol Number).";
            type inet:ip-version;
         }
    }
    
    grouping ipv4-source-attributes {
        leaf ipv4-source {
            description "IPv4 source address.";
            type inet:ipv4-prefix;
        }
    }
    
    grouping ipv4-destination-attributes {
        leaf ipv4-destination {
            description "IPv4 destination address.";
            type inet:ipv4-prefix;
        }
    }

    grouping ipv6-source-attributes {
        leaf ipv6-source {
            description "IPv6 source address.";
            type inet:ipv6-prefix;
        }
    }
    
    grouping ipv6-destination-attributes {
        leaf ipv6-destination {
            description "IPv6 destination address.";
            type inet:ipv6-prefix;
        }
    }
    
    grouping ipv6-nd-target-attributes {
        leaf ipv6-nd-target {
            description "IPv6 target address for neighbour discovery message";
            type inet:ipv6-address;
        }
    }
    
    grouping ipv6-label-attributes {
        leaf ipv6-flabel {
            type inet:ipv6-flow-label;
        }
        // TODO is this a good name for this?
        leaf flabel-mask {
            type inet:ipv6-flow-label;
        }
    }
    
    grouping ipv6-nd-sll-attributes {
        leaf ipv6-nd-sll {
            description "Link layer source address for neighbour discovery message";
            type yang:mac-address;
        }
    }
    
    grouping ipv6-nd-tll-attributes {
        leaf ipv6-nd-tll {
            description "Link layer target address for neighbour discovery message";
            type yang:mac-address;
        }
    }
    
    grouping ipv6-ext-header-attributes {
        container "ipv6-ext-header" {
            leaf ipv6-exthdr {
                description "IPv6 Extension Header field";
                type uint16;
            }

            leaf ipv6-exthdr-mask {
                type uint16 {
                  range "0..512";
                }
            }
        }
    }

    grouping udp-source-port-attributes {
        leaf udp-source-port {
            description "UDP source port.";
            type inet:port-number;
        }
    }
    
    grouping udp-destination-port-attributes {
        leaf udp-destination-port {
            description "UDP destination port.";
                type inet:port-number;
        }
    }

    grouping mpls-label {
        leaf mpls-label {
            description "Label in the first MPLS shim header";
            type uint32;
        }
    }
    
    grouping mpls-tc {
        leaf mpls-tc {
            description "TC in the first MPLS shim header";
            type uint8;
        }
    }
    grouping mpls-bos {
        leaf mpls-bos {
            description "BoS bit in the first MPLS shim header";
            type uint8;
        }
    }
    
    grouping pbb {
        container "pbb" {
            leaf pbb-isid {
                description "I-SID in the first PBB service instance tag";
                type uint32;
            }

            leaf pbb-mask {
                type uint32 {
                  range "0..16777216";
                }
            }
        }
    }
    
    grouping "protocol-match-fields" {
        uses mpls-label;

        uses mpls-tc;

        uses mpls-bos;

        uses pbb;
    }

    grouping tcp-source-port-attributes {
        leaf tcp-source-port {
            description "TCP source port.";
            type inet:port-number;
        }
    }
    
    grouping tcp-destination-port-attributes {
        leaf tcp-destination-port {
            description "TCP destination port.";
            type inet:port-number;
        }
    }

    grouping sctp-source-port-attributes {
        leaf sctp-source-port {
            description "SCTP source port.";
            type inet:port-number;
        }
    }
    
    grouping sctp-destination-port-attributes {
        leaf sctp-destination-port {
            description "SCTP destination port.";
            type inet:port-number;
        }
    }
    
    grouping icmpv4-type {
        leaf icmpv4-type {
            description "ICMP type.";
            type uint8; // Define ICMP Type
        }
    }
    
    grouping icmpv4-code {
        leaf icmpv4-code {
            description "ICMP code.";
            type uint8; // Define ICMP Code
        }
    }

    grouping "icmpv4-match-fields" {
        uses icmpv4-type;
        uses icmpv4-code;
    }
    
    grouping icmpv6-type {
        leaf icmpv6-type {
            description "ICMP type.";
            type uint8; // Define ICMP Type
        }
    }
    
    grouping icmpv6-code {
        leaf icmpv6-code {
            description "ICMP code.";
            type uint8; // Define ICMP Code
        }
    }

    grouping "icmpv6-match-fields" {
        uses icmpv6-type;
        
        uses icmpv6-code;
    }
    
    grouping arp-op-attributes {
        leaf arp-op {
            type uint16; // TODO make semantic
        }
    }

    grouping arp-source-transport-address-attributes {
        leaf arp-source-transport-address {
            description "ARP source IPv4 address.";
            type inet:ipv4-prefix;
        }
    }
    
    grouping arp-target-transport-address-attributes {
        leaf arp-target-transport-address {
            description "ARP target IPv4 address.";
            type inet:ipv4-prefix;
        }
    }
    
    grouping arp-source-hardware-address-attributes {
        description "ARP source hardware address.";
        uses mac-address-filter;
    }
    
    grouping arp-target-hardware-address-attributes {
        description "ARP target hardware address.";
        uses mac-address-filter;
    }
    
    grouping tcp-flags-attributes {
        leaf tcp-flag {
            type uint16;  // TODO For the love of God can we make this semantic
        }
    }

    grouping tunnel-ipv4-source-attributes {
        leaf tunnel-ipv4-source {
            description "IPv4 source tunnel endpoint address.";
            type inet:ipv4-prefix;
        }
    }
    
    grouping tunnel-ipv4-destination-attributes {
        leaf tunnel-ipv4-destination {
            description "IPv4 destination tunnel endpoint address.";
            type inet:ipv4-prefix;
        }
    }
    
    grouping in-port {
        leaf in-port {
            type inv:node-connector-id;
        }
    }
    
    grouping in-phys-port {
        leaf in-phys-port {
            type inv:node-connector-id;
        }
    }
    
    grouping tunnel-id {
        container "tunnel" {
            leaf tunnel-id {
                description "Metadata associated in the logical port";
                type uint64;
            }

            leaf tunnel-mask {
                type uint64;
            }
        }
    }

    grouping match-list {
        list match {
            key "order";
            leaf order {
                type int32;
            }
            uses match-attributes;
        }
    }
    
    grouping match-attributes {
        choice match {
            case in-port-case {
                container in-port {
                    uses in-port;
                }
            }
            case in-phys-port-case {
                container in-phys-port {
                    uses in-phys-port;
                }
            }
            case metadata-case {
                container "metadata" {
                    uses of-metadata;
                }
            }
            
            case tunnel-case {
                uses tunnel-id;
            }
            
            case ethernet-source-case {
                container ethernet-source {
                    uses ethernet-source-attributes;
                }
            }
            
            case ethernet-destination-case {
                container ethernet-destination {
                    uses ethernet-destination-attributes;
                }
            }
            
            case ethernet-type-case {
                container ethernet-type {
                    uses ethernet-type-attributes;
                }
            }
            
            
            case vlan-match-case  {
                container "vlan-match" {
                    uses "vlan-match-fields";
                }
            }
            
            case ip-protocol-case {
                container ip-protocol {
                    uses ip-protocol-attributes;
                }
            }
            
            case ip-dscp-case {
                container ip-dscp {
                    uses ip-dscp-attributes;
                }
            }
            
            case ip-ecn-case {
                container ip-ecn {
                    uses ip-ecn-attributes;
                }
            }
            
            case ip-version-case {
                container ip-version {
                    uses ip-version-attributes;
                }
            }
            
            case ipv4-source-case {
                container ipv4-source {
                    uses ipv4-source-attributes;
                }
            }
            
            case ipv4-destination-case {
                container ipv4-destination {
                    uses ipv4-destination-attributes;
                }
            }
            
            case ipv6-source-case {
                container ipv6-source {
                    uses ipv6-source-attributes;
                }
            }
            
            case ipv6-destination-case {
                container ipv6-destination {
                    uses ipv6-destination-attributes;
                }
            }
            
            case ipv6-nd-target-case {
                container ipv6-nd-target {
                    uses ipv6-nd-target-attributes;
                }
            }
            
            case ipv6-label-case {
                container ipv6-label {
                    uses ipv6-label-attributes;
                }
            }
            
            case ipv6-nd-sll-case {
                container ipv6-nd-sll {
                    uses ipv6-nd-sll-attributes;
                }
            }
            
            case ipv6-nd-tll-case {
                container ipv6-nd-tll {
                    uses ipv6-nd-tll-attributes;
                }
            }
            
            case ipv6-ext-header-case {
                container ipv6-ext-header {
                    uses ipv6-ext-header-attributes;
                }
            }
            
            case arp-op-case {
                container arp-op {
                    uses arp-op-attributes;
                }
            }
            
            case arp-source-transport-address-case {
                container arp-source-transport-address {
                    uses arp-source-transport-address-attributes;
                }
            }
            
            case arp-target-transport-address-case {
                container arp-target-transport-address {
                    uses arp-target-transport-address-attributes;
                }
            }
            
            case arp-source-hardware-address-case {
                container arp-source-hardware-address {
                    uses arp-source-hardware-address-attributes;
                }
            }
            
            case arp-target-hardware-address-case {
                container arp-target-hardware-address {
                    uses arp-target-hardware-address-attributes;
                }
            }
            
            case tunnel-ipv4-source-case {
                container tunnel-ipv4-source {
                    uses tunnel-ipv4-source-attributes;
                }
            }
            
            case tunnel-ipv4-destination-case {
                container tunnel-ipv4-destination {
                    uses tunnel-ipv4-destination-attributes;
                }
            }
            
            case tcp-source-port-case {
                container tcp-source-port {
                    uses tcp-source-port-attributes;
                }
            }
            
            case tcp-destination-port-case {
                container tcp-destination-port {
                    uses tcp-destination-port-attributes;
                }
            }
            
            case udp-source-port-case {
                container udp-source-port {
                    uses udp-source-port-attributes;
                }
            }
            
            case udp-destination-port-case {
                container udp-destination-port {
                    uses udp-destination-port-attributes;
                }
            }
            
            case sctp-source-port-case {
                container sctp-source-port-port {
                    uses sctp-source-port-attributes;
                }
            }
            
            case sctp-destination-port-case {
                container sctp-destination-port {
                    uses sctp-destination-port-attributes;
                }
            }
            
            case tcp-flags-case {
                container tcp-flags {
                    uses "tcp-flags-attributes";
                }
            }
            
            case icmpv4-match {
                container "icmpv4-match" {
                    uses "icmpv4-match-fields";
                }
            }
            case icmpv6-match-case {
                
            }
            case protocol-match-fields-case {
                container "protocol-match-fields" {
                    uses "protocol-match-fields";
                }
            }
        }
    }
}
