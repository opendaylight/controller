module opendaylight-queue-types {
    namespace "urn:opendaylight:flow:types:queue";
    prefix queue-types;

    import ietf-yang-types {prefix yang; revision-date "2010-09-24";}
    import opendaylight-inventory {prefix inv; revision-date "2013-08-19";}
    
    revision "2013-09-25" {
        description "Initial revision of Queue Inventory model";
    }
    
    typedef queue-id {
        type yang:counter32;
        description "id for the specific queue.";
    }
    
    typedef queue-properties-enum {
        type enumeration {
            enum min_rate;
            enum max_rate;
        }
    }

    grouping node-queue-config {
        list queues {
            key "queue-id";
            leaf queue-id {
                type queue-id;
                description "id for the specific queue.";
            }
            uses queue;
        }
    }

    grouping queue {
        leaf queue-id {
            type queue-id;
        }
        leaf port {
            type inv:node-connector-id;
        }
        list queue-properties {
            key "property-name";
            leaf property-name {
                type queue-properties-enum;
            }
            leaf property-value {
                type uint32;
            }
        }
    }
}
