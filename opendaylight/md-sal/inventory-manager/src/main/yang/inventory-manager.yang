module inventory-manager {

    yang-version 1;
    namespace "urn:opendaylight:params:xml:ns:yang:controller:md:sal:inventory-manager";
    prefix "inventory-manager";

    import config { prefix config; revision-date 2013-04-05; }
    import opendaylight-md-sal-binding { prefix mdsal; revision-date 2013-10-28; }

    description
        "This module contains the base YANG definitions for
        inventory-manager implementation.";

    revision "2014-09-25" {
        description
            "Initial revision.";
    }

    identity inventory-manager {
            base config:module-type;
            config:java-name-prefix InventoryManager;
    }

    augment "/config:modules/config:module/config:configuration" {
        case inventory-manager {
            when "/config:modules/config:module/config:type = 'inventory-manager'";

            container notification-service {
                uses config:service-ref {
                    refine type {
                        mandatory true;
                        config:required-identity mdsal:binding-notification-service;
                    }
                }
            }

            container data-broker {
                uses config:service-ref {
                    refine type {
                        mandatory false;
                        config:required-identity mdsal:binding-async-data-broker;
                    }
                }
            }
        }
    }
}
