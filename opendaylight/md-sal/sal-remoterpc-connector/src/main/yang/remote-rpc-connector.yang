module remote-rpc-connector {
	yang-version 1;
    namespace "urn:opendaylight:params:xml:ns:yang:controller:config:remote-rpc-connector";
    prefix "remote-rpc-connector";

    import config { prefix config; revision-date 2013-04-05; }
    import opendaylight-md-sal-dom {prefix dom;}
    import actor-system-provider-service {prefix actor-system;}

    description
        "This module contains the base YANG definitions for
                 the remote routed rpc";

    revision "2014-07-07" {
        description
            "Initial revision";
    }

    // This is the definition of the service implementation as a module identity.
    identity remote-rpc-connector {
      base config:module-type;
      // Specifies the prefix for generated java classes.
      config:java-name-prefix RemoteRPCBroker;
    }

    augment "/config:modules/config:module/config:configuration" {
        case remote-rpc-connector {
            when "/config:modules/config:module/config:type = 'remote-rpc-connector'";

            container dom-broker {
                uses config:service-ref {
                    refine type {
                        mandatory true;
                        config:required-identity dom:dom-broker-osgi-registry;
                    }
                }
            }

            container actor-system-provider {
                uses config:service-ref {
                    refine type {
                        mandatory false;
                        config:required-identity actor-system:actor-system-provider-service;
                    }
                }
            }

            leaf enable-metric-capture {
                default false;
                type boolean;
                description "Enable or disable metric capture.";
            }

            leaf bounded-mailbox-capacity {
                default 1000;
                type uint16;
                description "Max queue size that an actor's mailbox can reach";
            }
        }
    }

}
