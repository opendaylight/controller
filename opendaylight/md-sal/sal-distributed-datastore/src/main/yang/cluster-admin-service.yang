module cluster-admin-provider {
    yang-version 1;
    namespace "urn:opendaylight:params:xml:ns:yang:controller:config:cluster-admin-provider";
    prefix "cluster-admin-provider";

    import config { prefix config; revision-date 2013-04-05; }
    import opendaylight-operational-dom-datastore {prefix operational-dom-store-spi;}
    import opendaylight-config-dom-datastore {prefix config-dom-store-spi;}
    import opendaylight-md-sal-binding { prefix mdsal; revision-date 2013-10-28; }

    description
        "This module contains the configuration YANG definitions for the ClusterAdminRpcService implementation";

    revision "2015-10-13" {
        description "Initial revision.";
    }

    // This is the definition of the provider implementation as a module identity.
    identity cluster-admin-provider {
        base config:module-type;
        config:java-name-prefix ClusterAdminProvider;
    }

    //  Augments the 'configuration' choice node under modules/module.
    augment "/config:modules/config:module/config:configuration" {
        case cluster-admin-provider {
            when "/config:modules/config:module/config:type = 'cluster-admin-provider'";
                container config-data-store {
                    uses config:service-ref {
                        refine type {
                            mandatory true;
                            config:required-identity config-dom-store-spi:config-dom-datastore;
                        }
                    }
                }

                container oper-data-store {
                    uses config:service-ref {
                        refine type {
                            mandatory true;
                            config:required-identity operational-dom-store-spi:operational-dom-datastore;
                        }
                    }
                }

                container rpc-registry {
                    uses config:service-ref {
                        refine type {
                            mandatory true;
                            config:required-identity mdsal:binding-rpc-registry;
                        }
                    }
                }
        }
    }
}
