module prefix-shard-configuration {
    yang-version 1;
    namespace "urn:opendaylight:params:xml:ns:yang:controller:md:sal:clustering:prefix-shard-configuration";
    prefix "prefix-config";

    description
        "This module contains the base YANG definitions for
        shards based on prefix configuration";

    import shard-configuration {
        prefix "sc";
    }

    revision "2017-01-10" {
        description "Initial revision.";
    }

    container prefix-shards {

        list shard {
            key prefix;
            leaf prefix {
                type instance-identifier;
                description "Prefix that this shard is rooted at.";
            }

            container replicas {
                leaf-list replica {
                    type string;
                }

                description "List of cluster member nodes that this shard is replicated on";
            }

            uses sc:shard-persistence;

            description "List of prefix-based shards configured.";
        }
    }
}
