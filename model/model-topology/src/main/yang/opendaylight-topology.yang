module opendaylight-topology {
    yang-version 1;
    namespace "urn:opendaylight:model:topology:general";
    // replace with IANA namespace when assigned
    prefix "nt";

    import yang-ext { prefix "ext"; }
    import ietf-inet-types { prefix "inet"; }
    import network-topology {prefix "topo"; revision-date "2013-10-21"; }

    organization "TBD";

    contact "WILL-BE-DEFINED-LATER";

    revision 2013-10-30 {
        description
            "Initial revision.";
    }

    identity node-type {
    
    }
    
    typedef node-type-ref {
        type identityref {
            base node-type;
       }
    }
    
    identity topology-context {
    
    }
    
    identity topology-node-context {
        
    }

    grouping node-identifiers {
        list node-identifier {
            key "type identifier";
            leaf type {
                type node-type-ref;
            }
            leaf identifier {
                type inet:uri;
            }
        }
    }

    augment "/topo:network-topology/topo:topology" {
        ext:context-instance "topology-context";
    }

    /* Inventory Augmentations */
    augment "/topo:network-topology/topo:topology/topo:node" {
        ext:context-instance "topology-node-context";
    }

    augment "/topo:network-topology/topo:topology/topo:node" {
        ext:augment-identifier "identifiable-node";
        uses node-identifiers;
    }
}
