module ntfbench-payload {
    yang-version 1;
    namespace "urn:opendaylight:params:xml:ns:yang:ntfbench-payload";
    prefix "ntfbenchmark";

    description
        "Copyright © 2015, 2018 Cisco Systems, Inc. and others.

        This program and the accompanying materials are made available under the
        terms of the Eclipse Public License v1.0 which accompanies this distribution,
        and is available at http://www.eclipse.org/legal/epl-v10.html";

    revision "2015-07-09" {
        description "Initial revision of ntfbenchmark model";
    }

    grouping payload {
        list payload {
            description
                "The payload for the notification";
            key id;
            leaf id {
                type int32;
            }
        }
    }

    notification ntfbench {
        uses payload;
    }
}
